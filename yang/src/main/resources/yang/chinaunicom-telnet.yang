module chinaunicom-telnet {

  namespace "http://chinaunicom.com/yang/basicmanage/chinaunicom-telnet";
  prefix "telnet";
  
  import chinaunicom-acl { prefix "acl"; }

  organization "UTStarcom Telecom Co., Ltd.";

  contact
    "UTStarcom Telecom Co., Ltd.
     
     Postcode: 310053 
     Address: 368 Liuhe Road, Binjiang District,Hangzhou, Zhejiang

     E-mail: sheng.yu@utstar.com";
     
  description 
    "This module contains a collection of YANG definitions
     for UTStarcom IPRAN telnet configuration.
     Copyright (c) 2013-2020 by UTStarcom Telecom Co., Ltd.
     All rights reserved.";

  revision 2020-12-10{
      description 
        "First revision.";
  }

  container telnet {
    description 
      "The container defines the TELNET config.";

    container telnet-server {
      description 
        "The container defines the TELNET server config.";

      leaf acl-name {
        type acl:acl-name;
        description "acl name";		   
      }
    }
  }
}
