module chinaunicom-mpls-oper{

  /*** NAMESPACE / PREFIX DEFINITION ***/

  namespace "http://chinaunicom.com/yang/mplsprotocol/chinaunicom-mpls-oper";

  prefix "mpls-oper";

  /*** LINKAGE (IMPORTS / INCLUDES) ***/
  import chinaunicom-datatype-common { prefix "co-type"; }
  
  import ietf-inet-types { prefix "inet"; }
  
  import chinaunicom-mpls{ prefix "mpls"; }
  
  import chinaunicom-protectgroup-common{ prefix "protgrp-co"; }
  
  
  import chinaunicom-staticroute{ prefix "s-route"; }
	
  
  /*** META INFORMATION ***/

  organization "Fiberhome Systems, Inc.";

  contact
	"
	chinaunicom Communications Techlonogy Co., Ltd.
     Postcode: 100140 
     Address: No 21 ,Financial Street, Xicheng District, Beijing
     E-mail: ykou@chinaunicom.com
     
	Fiberhome Communications Techlonogy Co., Ltd.
	 Postcode: 430073 
	 Address: No.6,Gaoxin 4 Rd,Donghu Hi-Tech Development Zone, Wuhan, Hubei
	 E-mail: yang- author@fiberhome.com


	UTStarcom Telecom Co.,Ltd.
     Postcode: 310053 
     Address: 4th Floor, South Wing, 368 Liuhe Road, Binjiang District, Hangzhou 310053, Zhejiang Province, P.R.China
     E-mail: sihai.bao@utstar.com";


  description 
    "This module contains a collection of YANG definitions
     for  chinaunicom ip frr protect info.

     This module contains definitions
     for the following management objects:
       l3vpn: l3vpn configuration for all instances

     This YANG module augments the
       FH-chinaunicom-snmp-agent-cfg
     module with configuration data.

     Copyright (c) 2013-2017 by chinaunicom Systems, Inc;Fiberhome Systems, Inc.;UTStarcom, Inc.
     All rights reserved.";

  revision "2021-01-04" {
	description
	 "add primary-lsp-id &secondary-lsp-id";
  }
	
	 
  revision "2020-12-21" {
	description
	 "Delete functions not required in IPRAN WBS technical specification:
	 modfiy primary-lsp-id &secondary-lsp-id to primary-lsp-name &secondary-lsp-name respectively";
  }
	
  revision "2019-12-17" {
    description
      "Surport receive and send aps display-in-hex.";
  }		
  
  revision "2019-11-27" {
    description
      "Surport ilm total summary.";
  }	

  revision "2018-06-12" {
    description
      "chinaunicom V5 1.0 revision.";
  }	
  
   typedef seg-type {
    type enumeration {      
      enum adjacency {
        value 0;
        description "adjacency";
      }
	  enum node {
        value 1;
        description "node";
      }
    }
    description "seg-type";
  }  
  
    typedef nh-flag {
    type enumeration { 
      enum none {
        value 0;
        description "none";
      }	
      enum primary {
        value 1;
        description "primary";
      }
	  enum secondary {
        value 2;
        description "secondary";
      }
	  enum ecmp {
        value 3;
        description "ecmp";
      }	  
    }
    description "nh-flag";
  }

  typedef priority {
    type enumeration { 
      enum low {
        value 0;
        description "low";
      }	
      enum high {
        value 1;
        description "high";
      }
    }
    description "priority";
  }
  
    typedef ftn-type {
    type enumeration {      
      enum total {
        value 0;
        description "total";
      }	
      enum static {
        value 1;
        description "static";
      }
	  enum bgp {
        value 2;
        description "bgp";
      }
	  enum ldp {
        value 3;
        description "ldp";
      }
	  enum isis-sr {
        value 4;
        description "isis-sr";
      }
	  enum ospf-sr {
        value 5;
        description "ospf-sr";
      }	 
    }
    description "ftn-type";
  }
  
    typedef protocol {
    type enumeration { 
      enum staic {
        value 0;
        description "staic";
      }	
      enum ldp {
        value 1;
        description "ldp";
      }
	  enum bgp {
        value 2;
        description "bgp";
      }
	  enum rsvp {
        value 3;
        description "rsvp";
      }
	  enum l3vpn {
        value 4;
        description "l3vpn";
      }
	  enum isis {
        value 5;
        description "isis";
      }
	  enum ospf {
        value 6;
        description "ospf";
      }
	  enum srte {
        value 7;
        description "srte";
      }
    }
    description "protocol";
  } 
 

  typedef ilm-label-act {
    type enumeration {      
      enum label-tr {
        value 1;
        description "label-tr";
      }
	  enum ipop {
        value 2;
        description "ipop";
      }
	  enum pop-rf {
        value 3;
        description "pop-rf";
      }
	  enum swap {
        value 4;
        description "swap";
      }
	  enum push {
        value 5;
        description "push";
      }	 
    }
    description "ilm-label-act";
  }

   typedef nh-label-act {
    type enumeration {
      enum swap {
        value 0;
        description "swap";
      }	
      enum swap-push {
        value 1;
        description "swap-push";
      }
	  enum pop-go {
        value 2;
        description "pop-go";
      }
	  enum pop-push {
        value 3;
        description "pop-push";
      }
	  enum none {
        value 4;
        description "none";
      }
    }
    description "nh-label-act";
  }

   typedef next-hop-type {
    type enumeration {
      enum none {
        value 0;
        description "none";
      }	
      enum primary {
        value 1;
        description "primary";
      }
	  enum backup {
        value 2;
        description "backup";
      }
	  enum ecmp {
        value 3;
        description "ecmp";
      }
    }
    description "next-hop-type";
  }
   typedef active-state {
    type enumeration {
      enum inactive {
        value 0;
        description "inactive";
      }	
      enum active {
        value 1;
        description "active";
      }
    }
    description "active-state";
  }
  
  grouping basic-state{
    leaf ingress{
	    type inet:ipv4-address-no-zone;
		description "tunnel ingress";
	}					
	leaf egress{
		type inet:ipv4-address-no-zone;
		description "tunnel egress";
	}
    leaf primary-lsp-id{
		type uint16{
	        range "1..65535";
	    }		 
		description "primary lsp id";
	}						
    leaf primary-lsp-name{
		type mpls:exp-name;
		description "primary lsp name";
	}
	leaf secondary-lsp-id{
		type uint16{
	        range "1..65535";
	    }		 
		description "secondary lsp id";
	}	
	leaf secondary-lsp-name{
		type mpls:exp-name;	 
		description "secondary lsp name";
	}		
	leaf switch-state{
		type protgrp-co:lps-switch-state;	 
		description "switch status";
	}
	leaf primary-lsp-state{
		type protgrp-co:path-state;	 
		description "primary lsp status";
	}
	leaf secondary-lsp-state{
		type protgrp-co:path-state;	 
		description "secondary lsp status";
	}	
  }
  grouping detail-state{
        leaf return-mode{
			type protgrp-co:revertive-mode;			  
			description "return mode";
		}	
        leaf signal-protocol{
		    type mpls:signal-type;	 
		    description "signal protocol";
	    }		
		leaf hold-off-config-time{
		    type uint32{
                 range "0..255";
            }
			default 0;
			description "hold off config time";
		}					
		leaf wtr-config-time{
			type uint32{
                range "0..30";
            }
			default 5;
			description "wtr config time";
		}
		leaf primary-lsp-label{
			type string{
                length "1..129";
            }
			description "primary-lsp-label";
		}
		leaf secondary-lsp-label{
			type string{
                length "1..129";
            }
			description "secondary-lsp-label";
		}		
        leaf primary-if-name{
			type mpls:if-ref;
			description "primary if name";
		}
        leaf secondary-if-name{
			type mpls:if-ref;
			description "secondary if name";
		}	
        leaf protect-type{
			type mpls:protect-type;
			description "protect type";
		}					
		leaf alm-detect-mode{
			type protgrp-co:detect-mode;
			description "alarm detect mode";
		}					
		leaf pri-detect-id{
			type uint32{
				range "1..65534";
			}
		    description "primary detect id";
		}					
		leaf secondary-detect-id{
			type uint32{
				range "1..65534";
			}
			description "secondary detect id";
		}					
		leaf protect-entity-id{
			type uint32{
				range "1..32678";
			}
			description "protect entity id";
		}
  }
  
  grouping statistics {
    leaf rx-packs{
      type uint64;
      description "receive packets";
    }    	
	leaf tx-packs{
      type uint64;
      description "transmit packets";
    } 		
	leaf rx-bytes{
      type uint64;
      description "receive bytes";
    }    	
	leaf tx-bytes{
      type uint64;
      description "transmit bytes";
    }
	leaf rx-flow{
      type uint64;
      description "receive flow";
    }    	
	leaf tx-flow{
      type uint64;
      description "transmit flow";
    }
	leaf rx-pps{
      type uint64;
      description "receive packets per second";
    }    	
	leaf tx-pps{
      type uint64;
      description "transmit packets per second";
    }
	leaf rx-drop{
      type uint64;
      description "receive drop packets";
    } 
	leaf rx-drop-bytes{
      type uint64;
      description "receive drop bytes";
    } 
  }
  
  	grouping ftn-nh-state{
        leaf ftn-type{
			type ftn-type;
			description "ftn-type";
		}
		leaf ad-distance{
		    type uint16;
			description "Administrative distance";
		}
		leaf cost{
		    type uint32;
			description "cost";
		}	
        leaf nexthop{
			type inet:ip-address;			  
			description "nexthop";
		}	
        leaf nh-flag{
			type nh-flag;
			description "nexthop flag";
		}	
		 leaf out-label{
			type string {
				length "1..127";
			}
			description "out label";
		}	
		leaf out-if{
			type mpls:if-ref;
			description "out interface";
		}		
        leaf active-state{
			type active-state;
			description "active state";
		}	
        leaf priority{
			type priority;
			description "priority";
		}	
		leaf time{
			type string {
				length "1..25";
			}
			description "time";
		}	
        leaf priority-value{
			type uint16;
			description "inlabel";
		}	
    }
	grouping ilm-detail-state{
        leaf out-label{
			type string {
				length "1..127";
			}
			description "out label";
		}	
        leaf nh-label-act{
			type nh-label-act;
			description "nh-label-act";
		}
        leaf nexthop{
			type inet:ip-address-no-zone;			  
			description "nexthop";
		}	
        leaf nh-hop-type{
			type next-hop-type;
			description "nh-hop-type";
		}	
		 leaf active-state{
			type active-state;
			description "active-state";
		}		

		leaf out-if{
			type mpls:if-ref;
			description "out interface";
		}
    }
	
    container mpls-oper{
	    config false;
	    description "mpls oper container";
		container tunnel-protect-groups{ 
			description "tunnel-protect-groups"; 
			
			/* tunnel-protect SUM YANG Model */
			container tunnel-protect-sum {
			  config false;
			  description "tunnel-protect-sum";
			  
			  leaf tunnel-protect-summary{
				type uint32{
				  range "0..4294967295";
				}
				description "tunnel-protect-summary";
			  }
			}
			list tunnel-protect-group{
				key "tunnel-id";
				description "protect tunnel list.
				ingress and egress are not input parameters";				
				leaf tunnel-id{
					type mpls:tunnel-id;
					description "tunnel id";
				}				
				uses basic-state{
		        }
			}
			list tunnel-protect-detail{
				key "tunnel-id";
				description "protect tunnel detail list. ingress and egress are not input parameters";
				leaf tunnel-id{
					type mpls:tunnel-id;
					description "tunnel id";
				}
				uses basic-state{
		        }
				uses detail-state{
		        }
			}
	
			list sr-lsp-statistics{
				key "tunnel-id path-role";
				leaf tunnel-id{
					type mpls:tunnel-id;
					description "tunnel id";
				}
				leaf path-role{
					type mpls:path-role;
					description "lsp path role";
				}
				uses statistics{
		        }
			}
		}
		container sr-te-tunnel-paths{ 
			description "sr-te-tunnel-paths"; 
			
			/* tunnel-path SUM YANG Model */
			list sr-te-tunnel-path{
			  key "tunnel-id";
			  description "sr-te-tunnel-path";
			  
			    leaf tunnel-id{
					type mpls:tunnel-id;
					description "tunnel id";
				}	
			
				list lsp-path{
					key "lsp-type";
					description "lsp-path-hop-summary";				
					leaf lsp-id{
						type uint16;
						description "tunnel id";
					}
					leaf lsp-type{
						type mpls:lsp-type;
						description "lsp type";
					}
					
					list path-hops{
					    key "hop-index";
						description "path-hops";				
						leaf hop-index{
							type uint32;
							description "hop-index";
						}	
						leaf local-ip{
							type inet:ipv4-address-no-zone;
							description "local-ip";
						}	
						leaf nexthop-ip{
							type inet:ipv4-address-no-zone;
							description "nexthop-ip";
						}
						leaf sid-value{
							type uint32;
							description "sid value";
						}	
						leaf sid-value-type{
							type seg-type;
							description "sid-value-type";
						}						
					}		
				}				
			}
		}
		container ilm-states{ 
			description "ilm";
			
			/* ilm-states total SUM YANG Model */
			container ilm-total-sum {
			  config false;
			  description "ilm total sum";
			  
			  leaf ilm-total-summary{
				type uint32{
				  range "0..4294967295";
				}
				description "ilm total summary";
			  }
			}
			
				/* ilm SUM YANG Model */
			list ilm-sum {
			  key "protocol";
			  description "ilm-sum";
				  
			  leaf protocol{
				type protocol;
				description "protocol";
			  }
			  leaf ilm-summary{
				type uint32{
				  range "0..4294967295";
				}
				description "ilm-summary";
			  }
			}	
			
			list ilm-detail{
			  key "in-label";
			  description "ilm-detail list";				
			  leaf in-label{
				type uint32;
				description "in-label";
			  }	
			  leaf fec{
			    type string {
				  length "1..29";
				}
				description "fec";
			  }	
			  leaf protocol-type{
				type protocol;
				description "protocol";
			  }
			  leaf vrf-name{
				type co-type:vpn-name-with-global;
				description "vrf name";
			  }
			  leaf timestamp{
				type string {
				  length "1..25";
				}
				description "timestamp";
			  }
			  leaf ilm-label-act{
				type ilm-label-act;
				description "ilm-label-act";
			  }
              list nexthop-detail{
				description "nexthop-detail";	
                uses ilm-detail-state;						
				    
              }				
			}
			
		}
        container vrf-ftn-states{ 
			description "ftn states"; 
			
			list vrf-ftn-state{
				key "vrf-name af-mode";
				description "vrf ftn list";				
				leaf vrf-name{
					type co-type:vpn-name-with-global;
					description "vrf name";
				}	
                leaf af-mode{
					type s-route:af-mode-enum;
					description "Address family identifier mode";
				}	
				
				/* ftn SUM YANG Model */
			    list ftn-sum {
				  key "ftn-type";
			      description "ftn-sum";
			  
			      leaf ftn-type{
				    type ftn-type;
				    description "ftn-type";
			      }
				  
				  leaf ftn-summary{
				    type uint32{
				      range "0..4294967295";
				    }
				    description "ftn-summary";
			      }				  
			    }		
				
				/* prefix SUM YANG Model */
			    container prefix-sum {
			      description "prefix-sum";
				  
				  leaf prefix-summary{
				    type uint32{
				      range "0..4294967295";
				    }
				    description "prefix-summary";
			      }				  
			    }
			
			
			    list ftn-detail{
					key "destination tnnlidx";
				    description "route-detail list";				
				    leaf destination{
					    type inet:ip-prefix;
					    description "destination";
				    }
					leaf tnnlidx{
					    type uint32;
					    description "tnnlidx";
				    }
                    list nexthop-detail{
				        description "nexthop-detail";	
                        uses ftn-nh-state;						
				    
                    }				
			    }
			}
		}
	}
	
	/* LSP CMD RPC */
	rpc set-lsp-switch {
	  input {
		leaf tunnel-id{
			type mpls:tunnel-id;
			description "tunnel id";
		}		
	    leaf cmd-type{
		  type protgrp-co:lps-switch-cmd-type;
		  description "switch-cmd-type";
	    }
	  }
	}
}
