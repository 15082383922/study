module chinaunicom-ntp {

  /*** NAMESPACE / PREFIX DEFINITION ***/
  namespace "http://chinaunicom.com/yang/systemmanage/chinaunicom-ntp";
  prefix "ntp";

  /*** LINKAGE (IMPORTS / INCLUDES) ***/
  import ietf-inet-types { prefix "inet"; }
  import chinaunicom-datatype-common { prefix "co-type"; }
  import chinaunicom-interface-common { prefix "if"; }

  organization "Fiberhome Systems, Inc.";

  contact
    "Fiberhome Communications Techlonogy Co., Ltd.

     Postcode: 430073
     Address: No.6,Gaoxin 4 Rd,Donghu Hi-Tech Development Zone, Wuhan, Hubei

     E-mail: jliu103@fiberhome.com";

  description
    "This module contains a collection of YANG definitions
     for Fiberhome chinaunicomV5R2 ntp package configuration.

     This module contains definitions for the following management objects:
       ntp: refclock config
	   ntp: unicast config
	   ntp: vrf config
	   ntp: authentication config

     Copyright (c) 2013-2016 by Fiberhome Systems, Inc.
     All rights reserved.";

  revision 2019-03-28 {
    description "Initial version.";
  }
  
    /* Typedef Definitions */
  typedef if-ref {
    type union {
      type if:mgmt-name;
      type if:ethphy-name;
      type if:ethvir-name;
      type if:ethlag-name;
      type if:veth-name;
      type if:ethsub-name;
      type if:flexetunnel-name;
    }
  }	

  typedef unicast-configuration-type {
    type enumeration {
      enum client {
        value "3";
        description
          "Use client association mode. This device
          will not provide synchronization to the
          configured NTP server.";
      }
      enum peer {
        value "1";
        description
          "Use symmetric active association mode.
          This device may provide synchronization
          to the configured NTP server.";
      }
    }
    description
      "This defines NTP unicast mode of operation.";
  }   
  
  /* Configuration data nodes */
  container ntp {
    description
      "Configuration parameters for NTP.";
    
	container ntp-global {
      description
        "enable or disable ntp function.";
	  leaf ntp-enable {
        type co-type:is-enable;
        default "disable";	
	  }
	}
	
    container refclock-master {
      description
        "Configures the device as NTP server.";
	  leaf master-address {
        type inet:ipv4-address;
        default "127.127.1.0";
        description
          "Stratum level from which NTP
          clients get their time synchronized.";
      }
      leaf master-stratum {
        type uint32 {
		  range "1..15";
		}
        default "5";
        description
          "Stratum level from which NTP
          clients get their time synchronized.";
      }
    }	  

    container authentications {
      description
        "Configuration of authentication.";
      list authentication {
        key "key-id";
        description
          "List of authentications.";
		leaf key-id {
		  type uint32 {
			range "1..100";
		  }
		  description
			"Authentication key identifier.";
		}
		leaf password {
		  type string;
		  description
			"The password";
		}
      }
    }

    container authentication-reliables {
      description
        "trust the authentication.";
      list authentication-reliable {
        key "key-id";
        description
          "List of authentication-reliables.";
		leaf key-id {
		  type uint32 {
			range "1..100";
		  }
		  description
			"set the authentication key id reliable.";
		}
      }
    }
	
	container ntp-unicast-cfgs {
      description
        "Set ntp client or peer parameters";
		list ntp-unicast-cfg {
		  key "address configuration-mode vrf-name";
		  description
			"List of ntp-unicast-cfg.";
		  leaf address {
			type inet:ipv4-address;
			description
			  "ntp remote server ip.";
		  }
		  leaf configuration-mode {
			type unicast-configuration-type;
			description
			  "Type of unicast configuration";
		  }
		  leaf vrf-name {
			type co-type:vpn-name-with-global;
			description
			  "config vrf for this association, need vrf activate before use";		
		  }
		  leaf source-interface {
			type ntp:if-ref;
			description
			  "The interface whose IP address is used by this association
			  as the source address.";			
		  }
		  leaf version {
			type uint32 {
			  range "1..4";
			}
			default "3";
			description
			"Identify the ntp protocol version.";	
		  }
		  leaf key-id {
			type uint32 {
			  range "1..100";
			}	  
			description
			  "Identify the key-id in authentication keys.";
		  }
		  leaf maxpoll {
			type uint32 {
			  range "10..17";
			}
			default "10";
			description
			"maximum message send poll,this is the exponent of 2.";
		  }
		  leaf minpoll {
			type uint32 {
			  range "3..6";
			}
			default "6";
			description
			"minimum message send poll,this is the exponent of 2.";
		  }	  
		  leaf iburst {
			type co-type:is-enable;
			default "disable";
			description
			  "If set, a series of packets are sent instead of a single
			  packet within the initial synchronization interval to achieve
			  faster initial synchronization.";
		  }
		  leaf burst {
			type co-type:is-enable;
			default "disable";
			description
			  "If set, a series of packets are sent instead of a single
			  packet within each synchronization interval to achieve faster
			  synchronization.";
		  }
		  leaf preference {
			type co-type:is-enable;
			default "disable";
			description
			  "Whether this association is preferred.";
		  }
	    }	
	}
	
	container vrf-activates {
	  description
        "all vrf need to be activated before use.
		this vrf name will both be used by refclock-master and unicast config.
		but refclock-master config no need to indentify vrf name, 
		as more than one client may requset to server";
		list vrf-activate {
		  key "vrf-name";
		  description
			"allow ntp send message use this vrf.";
		  leaf vrf-name {
			type co-type:vpn-name-with-global;
			description
			"activate the vrf name.";
		  }
		}
	}
  }
}
