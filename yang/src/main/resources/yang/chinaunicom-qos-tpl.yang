submodule chinaunicom-qos-tpl {
/*** NAMESPACE / PREFIX DEFINITION ***/

  belongs-to chinaunicom-qos {
    prefix "qos";
  }

  // /*** LINKAGE (IMPORTS / INCLUDES) ***/
  import chinaunicom-qos-type{ prefix "qos-type"; }
  import chinaunicom-datatype-common { prefix "co-type"; }
 
  import ietf-inet-types { prefix "inet"; }
  
  import chinaunicom-interface-common  { prefix "if"; }
  
  import ietf-yang-types  { prefix "yang"; }
  
  /*import chinaunicom-acl  { prefix "acl"; }*/
  
  /*import chinaunicom-l2vpn { prefix "l2vpn";}*/
  
  import chinaunicom-l3vpn { prefix "l3vpn";}
  
  import chinaunicom-mpls { prefix "mpls";}
   
  import chinaunicom-evpn { prefix "evpn"; }

  /*** META INFORMATION ***/

  organization "UTstarcom,Inc.";

  contact
    "UTStarcom Telecom Co.,Ltd.
     Postcode: 310053 
     Address: 4th Floor, South Wing, 368 Liuhe Road, Binjiang District, Hangzhou 310053, Zhejiang Province, P.R.China
     E-mail: sihai.bao@utstar.com";


  description 
    "This module contains a collection of YANG definitions
     for qos package configuration.

     This module contains definitions
     for the following management objects:
       qos-type: qos configuration

     Copyright (c) 2013-2021 by UTStarcom Telecom Co.,Ltd.
     All rights reserved.";

  revision "2021-01-19" {
    description
      "modify evpn path and delete static-lsp";
  }	 

  revision "2019-11-12" {
    description
      "redir-cfgs.";
   }
   
 revision "2019-10-12" {
    description
      "match inner-sec.";
  }
  
 revision "2019-09-29" {
    description
      "match vni/url/range-port.";
  }
  revision "2019-09-06" {
    description
      "Hqos bound.";
  }
  revision "2018-05-23" {
    description
      "Init revision.";
  }
  /* typedefs */
  /*end typedefs */

  grouping qos-tpl {
    /*hqos-enable*/
    container hqos-enable-cfgs {
        list hqos-enable-cfg {
            key slot;
            leaf slot {
                type co-type:slot-num-string;
            }
            leaf hqos-enable {
                type co-type:is-enable;
            }
        }
    }
    /*traffic-class*/
    container traffic-class-cfgs {
        list traffic-class-cfg {
            key class-name;
            leaf class-name {
                type qos-type:class-name;
            }
            leaf operator {
                type enumeration {
                    enum any {
                        value 1;
                    }
                    enum all {
                        value 2;
                    }
                }
            }
            list match-acl-cfg {
                key acl-name;
                leaf acl-name {
                    type qos-type:acl-name;
                }
            }
            list match-mpls-cfg {
                key "exp";
                /* leaf stack {
                    type uint8 {
                        range "1..255";
                    }
                    description "1 represents the bottom of the stack "; 
                }
                leaf label {
                    type uint32 {
                        range "0..1048575";
                    }
                } */
                leaf exp {
                    type uint8 {
                        range "0..7";
                    }
                }
                /* leaf ttl-begin {
                    type uint8 {
                        range "0..255";
                    }
                    description "Now not support ttl-begin ,the value is 0.";
                }
                leaf ttl-end {
                    type uint8 {
                        range "0..255";
                    }
                } */
            }
            list match-src-mac-cfg {
            key src-mac;
            leaf src-mac {
                type yang:mac-address;
            }
        }
        list match-dst-mac-cfg {
            key dst-mac;
            leaf dst-mac {
                type yang:mac-address;
            }
        }
        list match-outer-8021p-cfg {
            key outer-8021p;
            leaf outer-8021p {
                type uint8 {
                    range "0..7";
                }
            }
        }
        list match-inner-8021p-cfg {
            key inner-8021p;
            leaf inner-8021p {
                type uint8 {
                    range "0..7";
                }
            }
        }
        list match-etype-cfg {
            key etype;
            leaf etype {
                type uint16 {
                    range "1536..65535";
                }
            }
        }
        list match-ipv4-dst-cfg {
            key ipv4-dst;
            leaf ipv4-dst {
                type inet:ipv4-prefix;
            }
        }
        list match-ipv4-src-cfg {
            key ipv4-src;
            leaf ipv4-src {
                type inet:ipv4-prefix;
            }
        }
        container match-inner-ipv4-dst-cfgs{
         list match-inner-ipv4-dst-cfg {
            key ipv4-dst;
            leaf ipv4-dst {
                type inet:ipv4-prefix;
            }
        }
        }
        
        container match-inner-ipv4-src-cfgs{
        list match-inner-ipv4-src-cfg {
            key ipv4-src;
            leaf ipv4-src {
                type inet:ipv4-prefix;
            }
        }
        }
        list match-ipv4-dst-port-cfg {
            key ipv4-dst-port;
            leaf ipv4-dst-port {
                type uint16 {
                    range "0..65535";
                }
            }
            leaf ipv4-dst-max-port {
                type uint16 {
                    range "0..65535";
                }
            }
        }
        list match-ipv4-src-port-cfg {
            key ipv4-src-port;
            leaf ipv4-src-port {
                type uint16 {
                    range "0..65535";
                }
            }
            leaf ipv4-src-max-port {
                type uint16 {
                    range "0..65535";
                }
            }
        }
        list match-ipv4-dscp-cfg {
            key ipv4-dscp;
            leaf ipv4-dscp {
                type uint8 {
                    range "0..63";
                }
            }
        }
        list match-ipv4-precedence-cfg {
            key ipv4-precedence;
            leaf ipv4-precedence {
                type uint8 {
                    range "0..7";
                }
            }
        }
        list match-ipv4-tos-cfg {
            key ipv4-tos;
            leaf ipv4-tos {
                type uint8 {
                    range "0..15";
                }
            }
        }
        list match-ipv4-protocol-cfg {
            key ipv4-protocol;
            leaf ipv4-protocol {
                type uint8 {
                    range "0..255";
                }
            }
        }
        list match-ipv4-fragment-type-cfg {
            key fragment-type;
            leaf fragment-type {
                type qos-type:fragment-type;
            }
        }
        list match-ipv6-dst-cfg {
            key ipv6-dst;
            leaf ipv6-dst {
                type inet:ipv6-prefix;
            }
        }
        list match-ipv6-src-cfg {
            key ipv6-src;
            leaf ipv6-src {
                type inet:ipv6-prefix;
            }
        }
        list match-ipv6-dst-port-cfg {
            key ipv6-dst-port;
            leaf ipv6-dst-port {
                type uint16 {
                    range "0..65535";
                }
            }
        }
        list match-ipv6-src-port-cfg {
            key ipv6-src-port;
            leaf ipv6-src-port {
                type uint16 {
                    range "0..65535";
                }
            }
        }
        list match-ipv6-dscp-cfg {
            key ipv6-dscp;
            leaf ipv6-dscp {
                type uint8 {
                    range "0..63";
                }
            }
        }
        list match-ipv6-precedence-cfg {
            key ipv6-precedence;
            leaf ipv6-precedence {
                type uint8 {
                    range "0..7";
                }
            }
        }
        list match-ipv6-tos-cfg {
            key ipv6-tos;
            leaf ipv6-tos {
                type uint8 {
                    range "0..15";
                }
            }
        }
        list match-ipv6-protocol-cfg {
            key ipv6-protocol;
            leaf ipv6-protocol {
                type uint8 {
                    range "0..255";
                }
            }
        }
        list match-outer-vlan-cfg {
            key "outer-vlan-id";
            leaf outer-vlan-id {
                type uint16 {
                    range "1..4094";
                }
            }
        }
        list match-inner-vlan-cfg {
            key "inner-vlan-id";
            leaf inner-vlan-id {
                type uint16 {
                    range "1..4094";
                }
            }
        }
        list match-interface-cfg{
             key "if-name";
             leaf if-name{
                type qos-type:if-ref;
                description "interface name";
               }
        }
        
     /*    list match-ipv4-quintuple-list {
            key "ipv4-dst ipv4-src ipv4-dst-port ipv4-src-port ipv4-protocol";
            leaf ipv4-dst {
                type inet:ipv4-address;
            }
            leaf ipv4-src {
                type inet:ipv4-address;
            }
            leaf ipv4-dst-port {
                type uint16 {
                    range "0..65535";
                }
            }
            leaf ipv4-src-port {
                type uint16 {
                    range "0..65535";
                }
            }
            leaf ipv4-protocol {
                type uint8 {
                    range "0..255";
                }
            }
            leaf time-range {
                type qos-type:time-range-name;
            }
        }
        list match-ipv6-quintuple-list {
            key "ipv6-dst ipv6-src ipv6-dst-port ipv6-src-port ipv6-protocol";
            leaf ipv6-dst {
                type inet:ipv6-address;
            }
            leaf ipv6-src {
                type inet:ipv6-address;
            }
            leaf ipv6-dst-port {
                type uint16 {
                    range "0..65535";
                }
            }
            leaf ipv6-src-port {
                type uint16 {
                    range "0..65535";
                }
            }
            leaf ipv6-protocol {
                type uint8 {
                    range "0..255";
                }
            }
            leaf time-range {
                type qos-type:time-range-name;
            }
        } */
        list match-qos-id-cfg {
            key qos-id;
            leaf qos-id {
                type uint8 {
                    range "1..255";
                }
            }
        }
        container match-vni-cfgs
          {
            list match-vni-cfg {
            key vni-id;
            leaf vni-id {
                type uint32 {
                    range "0..4294967295";
                }
            }
          }
        }
        
        container match-url-cfgs
         {
           list match-url-cfg {
            key url;
            leaf url {
                type inet:uri;
              } 
           }
        }
		container match-ethertype-offset-cfg
		{
			container offset1{
			   leaf offset-value1 {
					type uint32 {
						range "0..60";
					}
					mandatory true;
			   }
			   leaf match-value1 {
					type uint32 {
						range "0..4294967295";
					}
					mandatory true;
					description "The input format is hexBinary.";
			   }
			   leaf match-mask1 {
					type uint32 {
						range "0..4294967295";
					}
					mandatory true;
					description "The input format is hexBinary.";
			   }
			}
		   
			container offset2{
			   leaf offset-value2 {
					type uint32 {
						range "0..60";
					}
			   }
			   leaf match-value2 {
					type uint32 {
						range "0..4294967295";
					}
					description "The input format is hexBinary.";
			   }
			   leaf match-mask2 {
					type uint32 {
						range "0..4294967295";
					}
					description "The input format is hexBinary.";
			   }
			}
		   
			container offset3{
			   leaf offset-value3 {
					type uint32 {
						range "0..60";
					}
			   }
			   leaf match-value3 {
					type uint32 {
						range "0..4294967295";
					}
					description "The input format is hexBinary.";
			   }
			   leaf match-mask3 {
					type uint32 {
						range "0..4294967295";
					}
					description "The input format is hexBinary.";
			   }
			}
		   
			container offset4{
			   leaf offset-value4 {
					type uint32 {
						range "0..60";
					}
			   }
			   leaf match-value4 {
					type uint32 {
						range "0..4294967295";
					}
					description "The input format is hexBinary.";
			   }
			   leaf match-mask4 {
					type uint32 {
						range "0..4294967295";
					}
					description "The input format is hexBinary.";
				}
			}			
			
		}
        }
        
    }
    
    /*traffic-policy*/
    container traffic-policy-cfgs {
        list traffic-policy-cfg {
            key policy-name;
            leaf policy-name {
                type qos-type:policy-name;
            }
            list cb-cfg {
                key class-name;
                leaf class-name {
                    type qos-type:class-name;
                }
                container traffic-behavior {
                    leaf action {
                        type qos-type:tpl-action;
                    }
                    container car-cfg {
                       when "../action = 'pass'";
                        leaf cir {
                            type uint32 {
                                range "0..4294967295";
                            }
                            description "The unit is kbps";
                            default "0";
                        }
                        leaf pir {
                        when "../car-mode != 'rfc2697-trtcm'";
                            type uint32 {
                                range "0..4294967295";
                            }
                            description "The unit is kbps";
                            default "4294967295";
                        }
                        leaf cbs {
                            type uint32 {
                                range "0..4294967295";
                            }
                            description "The unit is Byte";
                            default "4294967295";
                        }
                        leaf pbs {
                            type uint32 {
                                range "0..4294967295";
                            }
                            description "The unit is Byte";
                            default "4294967295";
                        }
                        leaf green-action {
                            type qos-type:car-action;
                            default "pass";
                        }
                        leaf green-mark-phb {
                            type qos-type:phb-value;
                            default "be";
                        }
                        leaf green-mark-color {
                            type qos-type:color;
                            default "green";
                        }
                        leaf yellow-action {
                            type qos-type:car-action;
                            default "pass";
                        }
                        leaf yellow-mark-phb {
                            type qos-type:phb-value;
                            default "be";
                        }
                        leaf yellow-mark-color {
                            type qos-type:color;
                            default "yellow";
                        }
                        leaf red-action {
                            type qos-type:car-action;
                            default "drop";
                        }
                        leaf red-mark-phb {
                            type qos-type:phb-value;
                            default "be";
                        }
                        leaf red-mark-color {
                            type qos-type:color;
                            default "red";
                        }
                        leaf car-mode {
                            type qos-type:car-mode;
                            default "rfc-mef";
                        }
                        leaf color-aware {
                            type qos-type:color-aware;
                            default "blind";
                        }
                    }
                    
                    container mark-phb-cfg {
                        leaf phb-value{
                            type qos-type:phb-value;
                            mandatory true;
                        }
                       leaf mark-color {
                            type qos-type:color;
                            mandatory true;
                            }                                           
                    }
                    
                    container scheduling-cfg {
                        leaf sch-mode {
                            type qos-type:scheduling-mode;
                            default "sq";
                        }
                        leaf wfq-value {
                            when "../sch-mode = 'wfq'";
                            type uint8 {
                                range "0..100";
                            }
                        }
                    }
                    container shaping-cfg {
                        leaf cir {
                            type uint32 {
                                range "0..4294967295";
                            }
                            description "The unit is kbps.The default value is the band width of the port";
                        }
                        leaf pir {
                            type uint32 {
                                range "0..4294967295";
                            }
                            description "The unit is kbps.The default value is the band width of the port";
                        }
                        leaf cbs {
                            type uint32 {
                                range "0..4294967295";
                            }
                            description "The unit is Byte";
                            default "4294967295";
                        }
                        leaf pbs {
                            type uint32 {
                                range "0..4294967295";
                            }
                            description "The unit is Byte";
                            default "4294967295";
                        }
                    }
                    container redir-cfg {
                       when "../action = 'pass'";
                        leaf redir-type {
                            type qos-type:redir-type;
                        }
                        leaf redir-vrf-name {
                          when "../redir-type != 'if'";
                            type qos-type:vrf-ref;
                        }
                        leaf redir-if-name {
                            type qos-type:if-ref;
                        }
                        leaf redir-cpu-enable{
                           when "../redir-type = 'if'";
                           type co-type:is-enable;
                        }
                        leaf redir-next-ipv4 {
                           must "(../redir-type = 'ipv4' and ../redir-next-ipv4 != '0.0.0.0')"{
                             error-message
                                "redir-type conflict with redir-next-ipv4.";
                              }
                            type inet:ipv4-address-no-zone;
                        }
                        leaf redir-next-ipv6 {
                            must "(../redir-type = 'ipv6' and ../redir-next-ipv6 != '0::0')"{
                             error-message
                                "redir-type conflict with redir-next-ipv6.";
                              }
                            type inet:ipv6-address-no-zone;
                        }
                    }
                    container mirror-cfg {
                       when "../action = 'pass'";
                        leaf mirror-to-type {
						     
                            type qos-type:mirror-to-type;
                        }
                        leaf mirror-if-name {
                            when "../mirror-to-type = 'interface'";
                            type qos-type:if-ref;
                        }
                    }
                    container remark-cfg {
                       when "../action = 'pass'";
                        leaf remark-type {
                            type qos-type:priority-type;
                        }
                        leaf remark-priority {
                                          when "../remark-type != 'dscp'";
                            type uint8 {
                                range "0..7";
                            }
                        }
                        leaf remark-dscp {
                            when "../remark-type = 'dscp'";
                            type uint8 {
                                range "0..63";
                            }
                        }
                    }
                }
                container queue-behavior-cfgs{
                    list queue-behavior-cfg {
                        key queue-id;
                        leaf queue-id {
                            type qos-type:phb-value;
                        }
                        container queue-behavior {

                            container scheduling-cfg {
                                leaf sch-mode {
                                    type qos-type:scheduling-mode;
                                    default "sq";
                                }
                                leaf wfq-value {
                                    when "../sch-mode = 'wfq'";
                                    type uint8 {
                                        range "0..100";
                                    }
                                }
                            }
                            container shaping-cfg {
                                leaf cir {
                                    type uint32 {
                                        range "0..4294967295";
                                    }
                                    description "The unit is kbps.The default value is the band width of the port";
                                }
                                leaf pir {
                                    type uint32 {
                                        range "0..4294967295";
                                    }
                                    description "The unit is kbps.The default value is the band width of the port";
                                }
                                leaf cbs {
                                    type uint32 {
                                        range "0..4294967295";
                                    }
                                    description "The unit is Byte";
                                    default "4294967295";
                                }
                                leaf pbs {
                                    type uint32 {
                                        range "0..4294967295";
                                    }
                                    description "The unit is Byte";
                                    default "4294967295";
                                }
                            }
                            container congestion-cfg {
                                leaf congestion-mode {
                                    type qos-type:congestion-mode;
                                    default "tail";
                                }
                                leaf wred-name {
                                    when "../congestion-mode = 'wred'";
                                    type qos-type:wred-name;
                                }
                            }
                            leaf size {
                                type uint32 {
                                    range "0..50000";
                                }
                                default "0";
                                description "The unit is KB";
                            }
                          }
                    }
                }
                
            }
        }
    }
  
    /*user-group */
    container user-group-policy-cfgs {
        list user-group-policy-cfg {
            key user-group-name;
            leaf user-group-name {
                type qos-type:user-group-name;
            }
            leaf outbound-policy-name {
                type qos-type:policy-name;
            }
        }
    }
  /*end tpl cfg*/
  }
    
    augment "/if:if/if:interfaces/if:interface" 
    {
      container qos-policy-cfgs{
        list qos-policy-cfg {
          key policy_direct;
            leaf policy_direct {
                type qos-type:direction-type;
            }
            leaf fq-policy-name {
                type qos-type:policy-name;
            }
         }
        }
        container hqos-policy-cfg {
            leaf fq-policy {
                type qos-type:policy-name;
            }
            leaf sq-policy {
                type qos-type:policy-name;
            }
            leaf user-group-name {
                type qos-type:user-group-name;
            }
        }
    }
    
    augment "/evpn:evpn/evpn:evpn-vpws/evpn:evpn-vpws-list"  
    {
        container hqos-policy-inbound-cfg {
                leaf fq-policy {
                  must '../sq-policy' {
                    error-message
                        "When fq-policy is set, sq-policy must also be set.";
                }
                    type qos-type:policy-name;
                }
                leaf sq-policy {
                    type qos-type:policy-name;
                }
        }
    }
    
    augment "/evpn:evpn/evpn:evpn/evpn:evpn-list"
    {
        container hqos-policy-inbound-cfg {
                leaf fq-policy {
                  must '../sq-policy' {
                    error-message
                        "When fq-policy is set, sq-policy must also be set.";
                }
                    type qos-type:policy-name;
                }
                leaf sq-policy {
                    type qos-type:policy-name;
                }
        }
    }
    
    augment "/l3vpn:l3vpn/l3vpn:vpn-instances/l3vpn:vpn-instance" 
    {
        container hqos-policy-inbound-cfgs {
             list hqos-policy-inbound-cfg {
                key "peer-ip";
                leaf peer-ip {
                    type inet:ipv4-address-no-zone;
                }
                leaf fq-policy {
                    type qos-type:policy-name;
                }
                leaf sq-policy {
                    type qos-type:policy-name;
                }
             }
        }
    }
    
    augment "/mpls:mpls/mpls:mpls-te/mpls:tunnel-te" 
    {
        container hqos-policy-inbound-cfg {
            list inbound-qos-policy{
            key qos_lsp_type;
            leaf qos_lsp_type {
                type qos-type:lsp-type;
            }
            leaf inbound-qos-policy {
                type qos-type:policy-name;
            }
            leaf fq-policy {
                must '../sq-policy' {
                    error-message
                        "When fq-policy is set, sq-policy must also be set.";
                 }
			    
                type qos-type:policy-name;
            }
            leaf sq-policy {
                type qos-type:policy-name;
            }
          }
        }
    }
  
  /*end*/
}
