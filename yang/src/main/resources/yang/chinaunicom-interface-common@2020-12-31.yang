module chinaunicom-interface-common {
    namespace "http://chinaunicom.com/yang/interface/chinaunicom-interface-common";
    prefix "if";
    import chinaunicom-datatype-common
    {
	revision-date 2020-08-14;
        prefix "co-type";
    }
	
	
    description "The module defined to config the interface common configures";
    
  revision 2020-12-31
  {
    description
      "add items for type ethphy-name,ethsub-name and flexephy";
  }
		   
  revision 2020-07-03
  {
    description
      "Absolute path modified to relative path. Modify ip-perfix type";
  }
    
    revision "2020-04-27" {
      description
        "modify dcn-name pattern.";
    } 
    
    revision 2020-03-24
    {
      description "add interface subclient";
    }

    revision "2020-01-08" {
      description
        "Add frame connection management interface name.";
    } 

    revision 2018-03-16;
    container if {
        container interfaces {
            list interface {
                key name;
                leaf name {
                    type union {
                        type if:lb-name;
                        type if:mgmt-name;
                        type if:null-name;
                        type if:tunnel-name;
                        type if:ethphy-name;
                        type if:ethvir-name;
                        type if:ethlag-name;
                        type if:veth-name;
                        type if:vcg-name;
                        type if:ethsub-name;
                        type if:sdhphy-name;
                        type if:sdhsys-name;
                        type if:vsdh-name;
                        type if:sdhvc4-name;
                        type if:sdhvc12-name;
                        type if:sdhvc3-name;
                        type if:pdhphy-name;
                        type if:ces-name;
                        type if:cep-name;
                        type if:otnphy-name;
                        type if:otnsys-name;
                        type if:otnoduk-name;
                        type if:wssphy-name;
                        type if:ampphy-name;
                        type if:oscphy-name;
                        type if:opmphy-name;
                        type if:otdrphy-name;
                        type if:otheroptphy-name;
                        type if:flexephy-name;
                        type if:flexegroup-name;
                        type if:flexeclient-name;
                        type if:flexetunnel-name;
                        type if:flexesubclient-name;
                        type if:dcn-name;
                        type if:virtual-overhead-name;
                        type if:bdif-name;
                        type if:wlan-name;
                        type if:lte-name;
                        type if:optm-name;
                        type if:flexo-name;
                        type if:vflexe-name;
                        type if:vlanif-name;
                        type if:pw-ve-name;
                    }
                }
                leaf type {
                    type if:if-type;
                    mandatory true;
                }
                leaf description {
                    type co-type:string128;
                }
                leaf enabled {
                    type co-type:is-enable;
                }
                leaf pm-statistic-enable
                {
                    when "../type = 'ETH-PHY' or
                        ../type = 'ETH-LAG' or
                        ../type = 'ETH-SUBIF' or
                        ../type = 'V-ETH' or
                        ../type = 'ETH-VIR' or
                        ../type = 'FLEXE-TUNNEL' or
                        ../type = 'FLEXE-CLIENT' or
                        ../type = 'FLEXE-SUBCLIENT'";
                    type co-type:is-enable;
                    default "disable";
                    description
                        "pm-statistic switch";
                }

		leaf is-uni 
		{
			mandatory true;
			type co-type:is-enable;
			description 
				"the uni or nni property";
		}
            }
        }
    }
    
    
    typedef if-type {
        type enumeration {
            enum LOOPBACK {
                value 0;
                description "lb-name";
            }
            enum MGMT {
                value 1;
                description "mgmt-name";
            }
            enum NULL {
                value 2;
                description "null-name";
            }
            enum TUNNEL {
                value 3;
                description "tunnel-name";
            }
            enum BDIF {
                value 4;
                description "bdif-name";
            }
            enum VLANIF {
                value 5;
                description "vlanif-name";
            }
            enum ETH-PHY {
                value 100;
                description "ethphy-name";
            }
            enum ETH-VIR {
                value 101;
                description "ethvir-name";
            }
            enum ETH-LAG {
                value 102;
                description "ethlag-name";
            }
            enum V-ETH {
                value 103;
                description "veth-name";
            }
            enum ETH-VCG {
                value 104;
                description "vcg-name";
            }
            enum ETH-SUBIF {
                value 105;
                description "ethsub-name";
            }
            enum PW-VE {
                value 106;
                description "pw-ve-name";
            }
            enum SDH-PHY {
                value 200;
                description "sdhphy-name";
            }
            enum SDH-SYS {
                value 201;
                description "sdhsys-name";
            }
            enum V-SDH {
                value 202;
                description "vsdh-name";
            }
            enum SDH-HP-VC4 {
                value 203;
                description "sdhvc4-name";
            }
            enum SDH-LP-VC12 {
                value 204;
                description "sdhvc12-name";
            }
            enum SDH-LP-VC3 {
                value 205;
                description "sdhvc3-name";
            }
            enum PDH-PHY {
                value 206;
                description "pdhphy-name";
            }
            enum PDH-SYS {
                value 207;
                description "pdhsys-name";
            }
            enum CES {
                value 208;
                description "ces-name";
            }
            enum CEP {
                value 209;
                description "cep-name";
            }
            enum OTN-PHY {
                value 300;
                description "otnphy-name";
            }
            enum OTN-SYS {
                value 301;
                description "otnsys-name";
            }
            enum OTN-ODUK {
                value 302;
                description "otnoduk-name";
            }
            enum WSS-PHY {
                value 303;
                description "wss-name";
            }
            enum AMP-PHY {
                value 304;
                description "amp-name";
            }
            enum OSC-PHY {
                value 305;
                description "osc-name";
            }
            enum OPM-PHY {
                value 306;
                description "opm-name";
            }
            enum OTDR-PHY {
                value 307;
                description "otdr-name";
            }
            enum OTHEROPT-PHY {
                value 308;
                description "otheropt-name";
            }
            enum OTN-OPTM {
                value 309;
                description "optm-name";
            }
            enum OTN-FLEXO {
                value 310;
                description "flexo-name";
            }
            enum OTN-VFLEXE {
                value 311;
                description "vflexe-name";
            }
            enum FLEXE-PHY {
                value 400;
                description "flexephy-name";
            }
            enum FLEXE-GROUP {
                value 401;
                description "flexegroup-name";
            }
            enum FLEXE-CLIENT {
                value 402;
                description "flexeclient-name";
            }
            enum FLEXE-TUNNEL {
                value 403;
                description "flexetunnel-name";
            }
            enum FLEXE-SUBCLIENT {
                value 404;
                description "flexesubclient-name";
            }            
            enum DCN {
                value 500;
                description "dcn-name";
            }
            enum VIRTUAL-OVERHEAD {
                value 600;
                description "virtual-overhead-name";
            }
            enum WLAN {
                value 700;
                description "wlan-name";
            }
            enum LTE {
                value 701;
                description "lte-name";
            }
        }
    }
    typedef lb-name {
        type co-type:string64 {
            pattern 'loopback\s{0,1}\d+' {
                description "loopback( |)<0-1023>";
            }
        }
        description "if-type=\"LOOPBACK\"";
    }
    typedef mgmt-name {
        type co-type:string64 {
            pattern 'mgmt\s{0,1}\d+/\d+/\d+/\d+' {
                description "mgmt( |)0/0/0/0";
            }
        }
        description "if-type=\"MGMT\"";
    }
    typedef null-name {
        type co-type:string64 {
            pattern 'null\s{0,1}\d+' {
                description "null( |)<0-15>";
            }
        }
        description "if-type=\"NULL\"";
    }
    typedef tunnel-name {
        type co-type:string64 {
            pattern 'tunnel\s{0,1}\d+' {
                description "tunnel( |)<1-8388607>";
            }
        }
        description "if-type=\"TUNNEL\"";
    }
    typedef ethphy-name {
        type co-type:string64 {
            pattern '(eth|eth-100mi|eth-1gi|eth-10gi|eth-25gi|eth-40gi|eth-50gi|eth-100gi|eth-200gi|eth-400gi)\s{0,1}\d+/\d+/\d+/\d+' {
                description "(eth|eth-100mi|eth-1gi|eth-10gi|eth-25gi|eth-40gi|eth-50gi|eth-100gi|eth-200gi|eth-400gi)( |)A/B/C/D";
            }
        }
        description "if-type=\"ETH-PHY\"";
    }
    typedef ethvir-name {
        type co-type:string64 {
            pattern 'virtual-ethernet\s{0,1}\d+/\d+/\d+/\d+' {
                description "virtual-ethernet( |)A/B/C/D";
            }
        }
        description "if-type=\"ETH-VIR\"";
    }
    typedef ethlag-name {
        type co-type:string64 {
            pattern 'lag\s{0,1}\d+' {
                description "lag( |)<1-64>";
            }
        }
        description "if-type=\"ETH-LAG\"";
    }
    typedef veth-name {
        type co-type:string64 {
            pattern 'pve\s{0,1}\d+' {
                description "pve( |)<1-2000>";
            }
        }
        description "if-type=\"V-ETH\"";
    }
    typedef vcg-name {
        type co-type:string64 {
            pattern 'vcg\s{0,1}\d+/\d+/\d+/\d+' {
                description "vcg( |)A/B/C/D";
            }
        }
        description "if-type=\"ETH-VCG\"";
    }
    typedef ethsub-name {
        type co-type:string64 {
            pattern '((eth|eth-100mi|eth-1gi|eth-10gi|eth-25gi|eth-40gi|eth-50gi|eth-100gi|eth-200gi|eth-400gi|virtual-ethernet)\s{0,1}\d+/\d+/\d+/\d+.\d+|(lag|pve|flexe-tunnel|pw-ve)\s{0,1}\d+.\d+)' {
                description "(eth|eth-100mi|eth-1gi|eth-10gi|eth-25gi|eth-40gi|eth-50gi|eth-100gi|eth-200gi|eth-400gi)( |)A/B/C/D.E
                     
							virtual-ethernet( |)A/B/C/D.E
                     
							lag( |)LAGNUM.SUBNUM
                     
							pve( |)PVENUM.SUBNUM

							flexe-tunnel( |)TUNNELNUM.SUBNUM
							
							pw-ve( |)PWVENUM.SUBNUM";
            }
        }
        description "if-type=\"ETH-SUBIF\"";
    }
    typedef sdhphy-name {
        type co-type:string64 {
            pattern '(stm-1i|stm-4i|stm-16i|stm-64i)\s{0,1}\d+/\d+/\d+/\d+' {
                description "(stm-1i|stm-4i|stm-16i|stm-64i)( |)A/B/C/D";
            }
        }
        description "if-type=\"SDH-PHY\"";
    }
    typedef sdhsys-name {
        type co-type:string64 {
            pattern '(b-stm-1i|b-stm-4i)\s{0,1}\d+/\d+/\d+/\d+' {
                description "(b-stm-1i|b-stm-4i)( |)A/B/C/D";
            }
        }
        description "if-type=\"SDH-SYS\"";
    }
    typedef vsdh-name {
        type co-type:string64 {
            pattern 'v-sdh\s{0,1}\d+' {
                description "v-sdh( |)<1-4095>";
            }
        }
        description "if-type=\"V-SDH\"";
    }
    typedef sdhvc4-name {
        type co-type:string64 {
            pattern '((au4i|b-au4i)\s{0,1}\d+/\d+/\d+/\d+/\d+|v-au4i\s{0,1}\d+/\d+)' {
                description "au4i( |)A/B/C/D/I

							v-au4i( |)A/B

							b-au4i( |)A/B/C/D/I";
            }
        }
        description "if-type=\"SDH-HP-VC4\"";
    }
    typedef sdhvc12-name {
        type co-type:string64 {
            pattern '((tu12i|b-tu12i)\s{0,1}\d+/\d+/\d+/\d+/\d+/\d+|v-tu12i\s{0,1}\d+/\d+/\d+)' {
                description "tu12i( |)A/B/C/D/I/J

							v-tu12i( |)A/B/C

							b-tu12i( |)A/B/C/D/I/J";
            }
        }
        description "if-type=\"SDH-LP-VC12\"";
    }
    typedef sdhvc3-name {
        type co-type:string64 {
            pattern '((tu3i|b-tu3i)\s{0,1}\d+/\d+/\d+/\d+/\d+/\d+|v-tu3i\s{0,1}\d+/\d+/\d+)' {
                description "tu3i( |)A/B/C/D/I/J

							v-tu3i( |)A/B/C

							b-tu3i( |)A/B/C/D/I/J";
            }
        }
        description "if-type=\"SDH-LP-VC3\"";
    }
    typedef pdhphy-name {
        type co-type:string64 {
            pattern '(e1i|e3i)\s{0,1}\d+/\d+/\d+/\d+' {
                description "(e1i|e3i)( |)A/B/C/D";
            }
        }
        description "if-type=\"PDH-PHY\"";
    }
    typedef ces-name {
        type co-type:string64 {
            pattern 'ces\s{0,1}\d+/\d+/\d+/\d+(/\d+/\d+){0,1}:\d+' {
                description "ces( |)(A/B/C/D:K|A/B/C/D/I/J:K)";
            }
        }
        description "if-type=\"CES\"";
    }
    typedef cep-name {
        type co-type:string64 {
            pattern 'cep\s{0,1}\d+/\d+/\d+/\d+/\d+/\d+' {
                description "cep( |)A/B/C/D/I/J";
            }
        }
        description "if-type=\"CEP\"";
    }
    typedef otnphy-name {
        type co-type:string64 {
            pattern '(otn-1g25i|otn-2g5i|otn-10gi|otn-25gi|otn-40gi|otn-50gi|otn-100gi|otn-200gi|otn-400gi)\s{0,1}\d+/\d+/\d+/\d+' {
                description "(otn-1g25i|otn-2g5i|otn-10gi|otn-25gi|otn-40gi|otn-50gi|otn-100gi|otn-200gi|otn-400gi)( |)A/B/C/D";
            }
        }
        description "if-type=\"OTN-PHY\"";
    }
    typedef otnsys-name {
        type co-type:string64 {
            pattern 'b-otn\s{0,1}\d+/\d+/\d+/\d+' {
                description "b-otn( |)A/B/C/D";
            }
        }
        description "if-type=\"OTN-SYS\"";
    }
    typedef otnoduk-name {
        type co-type:string64 {
            pattern '(\d+/\d+/\d+/\d+|optm-\d+|flexo-\d+|vflexe-\d+)(/(odu0|odu1|odu2|odu2e|odu3|odu3e1|odu3e2|odu3e|odu4|odu4e|oduflex|oduc1|oduc2|oduc4)-(\d+)){1,5}' {
            description "A/B/C/D/rate-i/rate-j (dimension variable)";
            }
        }
        description "if-type=\"OTN-ODUK\"";
    }
    typedef wssphy-name {
        type co-type:string64 {
            pattern 'wss\s{0,1}\d+/\d+/\d+/\d+' {
                description "wss( |)A/B/C/D";
            }
        }
        description "if-type=\"WSS-PHY\"";
    }
    typedef ampphy-name {
        type co-type:string64 {
            pattern 'amp\s{0,1}\d+/\d+/\d+/\d+' {
                description "amp( |)A/B/C/D";
            }
        }
        description "if-type=\"AMP-PHY\"";
    }
    typedef oscphy-name {
        type co-type:string64 {
            pattern 'osc\s{0,1}\d+/\d+/\d+/\d+' {
                description "osc( |)A/B/C/D";
            }
        }
        description "if-type=\"OSC-PHY\"";
    }
    typedef opmphy-name {
        type co-type:string64 {
            pattern 'opm\s{0,1}\d+/\d+/\d+/\d+' {
                description "opm( |)A/B/C/D";
            }
        }
        description "if-type=\"OPM-PHY\"";
    }
    typedef otdrphy-name {
        type co-type:string64 {
            pattern 'otdr\s{0,1}\d+/\d+/\d+/\d+' {
                description "otdr( |)A/B/C/D";
            }
        }
        description "if-type=\"OTDR-PHY\"";
    }
    typedef otheroptphy-name {
        type co-type:string64 {
            pattern 'extra\s{0,1}\d+/\d+/\d+/\d+' {
                description "extra( |)A/B/C/D";
            }
        }
        description "if-type=\"OTHEROPT-PHY\"";
    }
    typedef flexephy-name {
        type co-type:string64 {
            pattern '(flexe|flexe-50gi|flexe-100gi|flexe-200gi|flexe-400gi)\s{0,1}\d+/\d+/\d+/\d+' {
                description "(flexe|flexe-50gi|flexe-100gi|flexe-200gi|flexe-400gi)( |)A/B/C/D";
            }
        }
        description "if-type=\"FLEXE-PHY\"";
    }
    typedef flexegroup-name {
        type co-type:string64 {
            pattern 'flexe-group\s{0,1}\d+' {
                description "flexe-group( |)<1-1048574>";
            }
        }
        description "if-type=\"FLEXE-GROUP\"";
    }
    typedef flexeclient-name {
        type co-type:string64 {
            pattern 'flexe-client\s{0,1}\d+/\d+' {
                description "flexe-client( |)(GID/CID),GID range is 1 to 1048574,CID range is 1 to 65534";
            }
        }
        description "if-type=\"FLEXE-CLIENT\"";
    }
    typedef flexetunnel-name {
        type co-type:string64 {
            pattern 'flexe-tunnel\s{0,1}\d+' {
                description "flexe-tunnel( |)<1-65535>";
            }
        }
        description "if-type=\"FLEXE-TUNNEL\"";
    }
    typedef flexesubclient-name {
        type co-type:string64 {
            pattern 'flexe-subclient\s{0,1}\d+/\d+/\d' {
                description "flexe-subclient( |)(GID/CID/SID),GID range is 1 to 1048574,CID range is 1 to 65534,SID range is 1 to 65534";
            }
        }
        description "if-type=\"FLEXE-SUBCLIENT\"";
    }

    typedef dcn-name {
        type co-type:string64 {
            pattern '(dcn-serial|dcn-tunnel)\s{0,1}\d+/\d+/\d+/\d+(.\d+){0,1}|dcn-serial-flexe-tnl\s{0,1}\d+(.\d+){0,1}' {
                description "(dcn-serial|dcn-tunnel)( |)A/B/C/D(.E|)
				                     
							dcn-serial-flexe-tnl( |)<1-65535>(.NUM|)";
            }
        }
        description "if-type=\"DCN\"";
    }
    typedef virtual-overhead-name {
        type co-type:string64 {
            pattern 'virtual-overhead\s{0,1}\d+/\d+/\d+/\d+' {
                description "virtual-overhead( |)A/B/C/D";
            }
        }
        description "if-type=\"VIRTUAL-OVERHEAD\"";
    }
    typedef bdif-name {
        type co-type:string64 {
            pattern 'bdif\s{0,1}\d+' {
                description "bdif( |)<1-1048575>";
            }
        }
        description "if-type=\"BDIF\"";
    }
    typedef wlan-name {
        type co-type:string64 {
            pattern 'wlan\s{0,1}\d+/\d+/\d+/\d+' {
                description "wlan( |)A/B/C/D";
            }
        }
        description "if-type=\"WLAN\"";
    }
    typedef lte-name {
        type co-type:string64 {
            pattern 'lte\s{0,1}\d+/\d+/\d+/\d+' {
                description "lte( |)A/B/C/D";
            }
        }
        description "if-type=\"LTE\"";
    }
    typedef optm-name {
        type co-type:string64 {
            pattern 'optm\s{0,1}\d+' {
                description "optm( |)<1-1048575>";
            }
        }
        description "if-type=\"OTN-OPTM\"";
    }
    typedef flexo-name {
        type co-type:string64 {
            pattern 'flexo\s{0,1}\d+' {
                description "flexo( |)<1-1048575>";
            }
        }
        description "if-type=\"OTN-FLEXO\"";
    }
    typedef vflexe-name {
        type co-type:string64 {
            pattern 'vflexe\s{0,1}\d+' {
                description "vflexe( |)<1-1048575>";
            }
        }
        description "if-type=\"OTN-VFLEXE\"";
    }
    typedef vlanif-name {
        type co-type:string64 {
            pattern 'vlanif\s{0,1}\d+' {
                description "vlanif( |)<1-1048575>";
            }
        }
        description "if-type=\"VLANIF\"";
    }
    typedef pw-ve-name {
        type co-type:string64 {
            pattern 'pw-ve\s{0,1}\d+' {
                description "pw-ve( |)<1-65535>";
            }
        }
        description "if-type=\"PW-VE\"";
    }
    typedef fcmt-name {
        type co-type:string64 {
            pattern 'fcmt-eth\s{0,1}\d+/\d+' {
                description "fcmt-eth( |)A/D, A=shelf id, D=port id";
            }
        }
        description "frame connection management";
    }
}
