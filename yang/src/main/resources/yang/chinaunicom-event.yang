module chinaunicom-event {
  namespace "http://chinaunicom.com/yang/systemmanage/chinaunicom-event";
  prefix event;

  import ietf-yang-types {
    prefix yang;
  }

  organization
    "Fiberhome Telecommunication Co., Ltd";
  contact
    "Fiberhome Systems, Inc.
     Postcode: 430073
     Address: No.6,Gaoxin 4 Rd,Donghu Hi-Tech Development Zone, Wuhan, Hubei
     Tel: +XXXXXXXXXXXX
     
     E-mail: yang-author@fiberhome.com";

  description
    "This module defines an interface for managing events.
     Main features of this module include:
       * Event list:
                 A list of all events.";

  revision 2018-11-22 {
    description
      "Initial revision.";
  }

  /*
   * Common types
   */

  typedef resource {
    type union {
      type instance-identifier {
        require-instance false;
      }
      type yang:object-identifier;
      type string;
      type yang:uuid;
    }
    description
      "This is an identification of the alarming resource, such as an
       interface.  It should be as fine-grained as possible both to
       guide the operator and to guarantee uniqueness of the alarms.
       If the alarming resource is modelled in YANG, this type will
       be an instance-identifier.
       If the resource is an SNMP object, the type will be an
       object-identifier.
       If the resource is anything else, for example a distinguished
       name or a CIM path, this type will be a string.
       If the alarming object is identified by a UUID use the uuid
       type.  Be cautious when using this type, since a UUID is hard
       to use for an operator.
       If the server supports several models, the presedence should
       be in the order as given in the union definition.";
  }

  typedef severity {
    type enumeration {
      enum indeterminate {
        value 2;
        description
          "Indicates that the severity level could not be
           determined.  This level SHOULD be avoided.";
      }
      enum minor {
        value 3;
        description
          "The 'minor' severity level indicates the existence of a
           non-service affecting fault condition and that corrective
           action should be taken in order to prevent a more serious
           (for example, service affecting) fault.  Such a severity
           can be reported, for example, when the detected alarm
           condition is not currently degrading the capacity of the
           resource.";
      }
      enum warning {
        value 4;
        description
          "The 'warning' severity level indicates the detection of a
           potential or impending service affecting fault, before any
           significant effects have been felt.  Action should be
           taken to further diagnose (if necessary) and correct the
           problem in order to prevent it from becoming a more
           serious service affecting fault.";
      }
      enum major {
        value 5;
        description
          "The 'major' severity level indicates that a service
           affecting condition has developed and an urgent corrective
           action is required.  Such a severity can be reported, for
           example, when there is a severe degradation in the
           capability of the resource and its full capability must be
           restored.";
      }
      enum critical {
        value 6;
        description
          "The 'critical' severity level indicates that a service
           affecting condition has occurred and an immediate
           corrective action is required.  Such a severity can be
           reported, for example, when a resource becomes totally out
           of service and its capability must be restored.";
      }
    }
    description
      "The severity level of the alarm.  Note well that value 'clear'
       is not included.  If an alarm is cleared or not is a separate
       boolean flag.";
  }


  /*
   * Groupings
   */

  grouping common-event-parameters {
    description
      "Common parameters for an event.
       This grouping is used both in the alarm list and in the
       notification representing an alarm state change.";
    leaf event-name {
      type string;
      description
        "This leaf provides the name of the event.";
    }
    leaf event-id {
      type uint32;
      mandatory true;
      description
        "This leaf provides a unique identification of the event.";
    }
    leaf resource {
      type resource;
      mandatory true;
      description
        "The alarming resource.  See also 'alt-resource'.  This could
         for example be a reference to the alarming interface";
    }
	leaf time {
      type yang:date-and-time;
      mandatory true;
      description
        "The time the status of the alarm changed.  The value
         represents the time the real alarm state change appeared in
         the resource and not when it was added to the alarm
         list.  The /alarm-list/alarm/last-changed MUST be set to the
         same value.";
    }
    leaf perceived-severity {
      type severity;
      mandatory true;
      description
        "The severity of the alarm as defined by X.733.  Note that
         this may not be the original severity since the alarm may
         have changed severity.";
    }
    anyxml event-detail {
      description
        "A user friendly text describing the alarm state change.";
    }
  }


  /*
   * The /alarms data tree
   */

  container events {
    description
      "The top container for this module.";
    container event-list {
      config false;
      description
        "The events in the system.";
      list event {
        key "event-name event-id resource";
        description
          "The list of alarms.  Each entry in the list holds one
           alarm for a given alarm type and resource.  An alarm can
           be updated from the underlying resource or by the user.
           The following leafs are maintained by the resource:
           is-cleared, last-change, perceived-severity, and
           alarm-text.  An operator can change: operator-state and
           operator-text.
           Entries appear in the alarm list the first time an alarm
           becomes active for a given alarm-type and resource.
           Entries do not get deleted when the alarm is cleared, this
           is a boolean state in the alarm.
           Alarm entries are removed, purged, from the list by an
           explicit purge action.  For example, purge all alarms that
           are cleared and in closed operator-state that are older
           than 24 hours.  Purged alarms are removed from the alarm
           list.  If the alarm resource state changes after a purge,
           the alarm will reappear in the alarm list.
           Systems may also remove alarms based on locally configured
           policies which is out of scope for this module.";
        uses common-event-parameters;
      }
    }
  }

  /*
   * Notifications
   */

  notification event-notification {
    description
      "This notification is used to report a state change for an
       alarm.  The same notification is used for reporting a newly
       raised alarm, a cleared alarm or changing the text and/or
       severity of an existing alarm.";
    uses common-event-parameters;
  }
}
