module chinaunicom-isis {

  /*** NAMESPACE / PREFIX DEFINITION ***/

  namespace "http://chinaunicom.com/yang/ipprotocol/routing/chinaunicom-isis";

  prefix "isis";

  /*** LINKAGE (IMPORTS / INCLUDES) ***/

  import ietf-inet-types {	revision-date 2013-07-15; prefix "inet"; }


  import chinaunicom-datatype-common {	revision-date 2020-08-14; prefix "co-type"; }

  import chinaunicom-routemap {	revision-date 2019-12-30; prefix "routemap"; }

  import chinaunicom-interface-common {	revision-date 2020-12-31;prefix "if"; }

  import chinaunicom-ipprefix {	revision-date 2021-04-02; prefix "ipprefix"; }

  import chinaunicom-l3vpn {	revision-date 2019-10-24; prefix "l3vpn"; }

  /*** META INFORMATION ***/

  organization "Fiberhome Systems, Inc.";

  contact
    "Fiberhome Systems, Inc.
     
    Postcode: 430073 
    Address: No.6,Gaoxin 4 Rd,Donghu Hi-Tech Development Zone, Wuhan, Hubei
    Tel: +XXXXXXXXXXXX

    E-mail: yang- author@fiberhome.com";

  description
    "This module contains a collection of YANG definitions
    for Fiberhome FOS-R8000 clns-isis package configuration.

    This module contains definitions
    for the following management objects:
    isis: IS-IS configuration for all instances

    This YANG module augments the
    FH-FOS-R8000-snmp-agent-cfg
    module with configuration data.

    Copyright (c) 2013-2016 by Fiberhome Systems, Inc.
    All rights reserved.";
  
  revision "2021-03-25" {
    description 
    "modify â€˜wide-metirc-styleâ€? of the data type â€™Isis-metric-styleâ€? to â€˜wide-transition-metric-styleâ€? ";
  }

  revision "2019-09-29" {
    description "add wlan and lte in interface type";
  }
  
  revision "2019-09-10" {
    description
      "1.add leaf <fast-flood-num>
       2.add function node-protecting and rlfa in <frr-use-cand-onlies>
       3.add container <sd-metric>
       4.change lsp-gen-interval from 1..120 to 0..120
       5.change hello-interval from 1..65535 to 3..65535";      
  }
  
  revision "2018-04-11" {
    description
      "FOS R8000 6.0 revision.";
  }

  
  /****************** typedef start ******************/ 

  typedef isis-redistribute-instance-name{
    type union {
      type string{
        length "1..32";
      }
      type string {
        pattern "nil";
      }
    }
  }

  typedef Isis-configurable-levels {
    type enumeration {
      enum level1 {
        value 1;
        description "Level1";
      }
      enum level2 {
        value 2;
        description "Level2";
      }
      enum level1-and2 {
        value 3;
        description "Both Levels";
      }
    }
    description "Isis configurable levels";
  }

  typedef Isis-network-type{
    type enumeration {
      enum broadcast {
        value 1;
      }
      enum p-to-p {
        value 2;
      }
    }
  }

  typedef Isis-internal-level {
    type enumeration {
      enum level1 {
        value 1;
        description "Level1";
      }
      enum level2 {
        value 2;
        description "Level2";
      }
    }
    description "Isis internal level";
  }

  typedef Isis-redist-proto {
    type enumeration {
      enum static {
        value 1;
        description "Static";
      }
      enum connected {
        value 2;
        description "Connected";
      }
      enum rip {
        value 3;
        description "RIP";
      }
      enum bgp {
        value 4;
        description "BGP";
      }
      enum isis {
        value 5;
        description "ISIS";
      }
      enum ospf {
        value 6;
        description "OSPF";
      }
      enum ospfv3 {
        value 7;
        description "OSPFv3";
      }
      enum isis-sr-local{
        value 8;
      }
    }
    description "Isis redist proto";
  }

  typedef Isis-metric {
    type enumeration {
      enum internal {
        value 1;
        description "Internal metric";
      }
      enum external {
        value 2;
        description "External metric";
      }
    }
    description "Isis metric";
  }

  typedef Isis-metric-style {
    type enumeration {
      enum narrow-metric-style {
        value 1;
        description "narrow metric style";
      }
      enum wide-metric-style {
        value 2;
        description "wide metric style";
      }
      enum transition-metric-style{
        value 3;
      }
      enum narrow-transition-metric-style{
        value 4;
      }
      enum wide-transition-metric-style{
        value 5;
      }
    }
    description "Isis metric style";
  }

  typedef Isis-authentication-algorithm {
    type enumeration {
      enum simple {
        value 0;
      }
      enum md5 {
        value 1;
        description "HMAC-MD5 checksum";
      }
      enum cleartext {
        value 3;
        description "Cleartext password";
      }
    }
    description "Isis authentication algorithm";
  }

  typedef Isis-authentication-type {
    type enumeration {
      enum send-only {
        value 1;
      }
      enum validate {
        value 2;
      }
    }
    description "Isis authentication algorithm";
  }

  typedef Isis-level-to-level  {
    type enumeration {
      enum L1TOL2 {
        value 1;
      }
      enum L2TOL1 {
        value 2;
      }
    }
    description "Isis propagation direction.";
  }

  typedef Isis-access-list-type  {
    type string {
      length "0..32";
    }
    description "Isis propagation direction. ACL has no yang file, set len 32 temporarily.";
  }

  typedef Isis-hello-padding {
    type enumeration {
      enum sometimes {
        value 0;
        description "Pad Hellos during adjacency formation only";
      }
      enum never {
        value 1;
        description "Never pad Hellos";
      }
    }
    description "Isis hello padding";
  }

  typedef Isis-address-family {
    type enumeration {
      enum ipv4 {
        value 1;
        description "IPv4";
      }
      enum ipv6 {
        value 2;
        description "IPv6";
      }
    }
    description "Isis address family";
  }

  typedef Isis-sub-address-family {
    type enumeration {
      enum unicast {
        value 1;
        description "Unicast";
      }
      enum multicast {
        value 2;
        description "Multicast";
      }
    }
    description "Isis sub address family";
  }

  typedef Isis-adjacency-check-state {
    type enumeration {
      enum uncheck {
        value 1;
      }
      enum check {
        value 2;
      }
    }
  }

  typedef Isis-sid-type {
    type enumeration {
      enum absolute {
        value 1;
      }
      enum index {
        value 2;
      }
    }
  }

  typedef Isis-sr-lsp-trigger-type {
    type enumeration {
      enum none {
        value 0;
      }
      enum host {
        value 1;
      }
      enum ip-prefix {
        value 2;
      }
    }
  }

  typedef Isis-instance-name {
    type string {
      length "0..32";
    }
    description "Isis instance name.";
  }

  typedef Isis-route-policy-ref{
    type routemap:policy-name;
  }

  typedef Isis-ip-prefix-ref{
    type ipprefix:list-name;
  }

  typedef Isis-if-ref{
    type union {
      type if:lb-name;
      type if:tunnel-name;
      type if:ethphy-name;
      type if:ethvir-name;
      type if:ethlag-name;
      type if:veth-name;
      type if:ethsub-name;
      type if:flexetunnel-name;
      type if:mgmt-name;
      type if:wlan-name;
      type if:lte-name;
    }
  }

  typedef Isis-vrf-ref{
    type l3vpn:vpn-name;
  }

  typedef Isisphp-flag {
    type enumeration {
      enum enable {
        value 0;
        description "Enable PHP";
      }
      enum disable {
        value 1;
        description "Disable PHP";
      }
    }
    description "Isisphp flag";
  }

  typedef Isis-auth-snp-lsp {
    type enumeration{
      enum snp{
        value 1;
        description "Enable SNP";
      }
      enum lsp{
        value 2;
        description "LSP ONLY";
      }
    }
  }

  typedef Isis-hostname-enable{
    type enumeration{
      enum enable{
        value 1;
      }
      enum disable{
        value 2;
      }
    }
  }
  
  /****************** typedef end ******************/

  container isis {
    description "IS-IS configuration for all instances";

    container isis-instances {
      description "IS-IS instance configuration";
      
      list isis-instance {
        key "instance-name";
        description "Configuration for a single IS-IS instance";

        leaf instance-name {
          type Isis-instance-name;
          description "Instance identifier MUST-CONFIG";
        }

        list net {
          key "net-name";         
          description "Network Entity Title (NET)";
          leaf net-name {
            type string {
              length "0..51";
            }
            description "Network Entity Title MUST-CONFIG";
          }
        }

        leaf is-type {
          type Isis-configurable-levels;
          description "level1-and2 : 3 IS type of the IS-IS process";
        }
        
        leaf lsp-mtu {
          type uint32 {
            range "512..9600";
          }
          default "1492";
          units "byte";
          description "Bytes";
        }

        leaf ecmp-num { 
          type uint16{
            range "1..16";
          }
          description "the max-path of route";
        }
        
        leaf lsp-lifetime {
          description "Maximum LSP lifetime";              
          type uint32 {
            range "350..65535";
          }
          default "1200";
          units "second";
        }       

        leaf fast-flood-num{
          description "the number of fast-flood routes";
          type uint32 {
            range "1..50";           
          }
          default "20";
        }
        
        list metric-style {
          key "level";
          description "Configuration of metric style in LSPs";
          leaf level {
            type Isis-internal-level;
            description "Level to which configuration applies";
          }
          leaf style {
            type Isis-metric-style;
            description "Metric Style";
          }
        }

        container sr-mpls {    
          leaf sr-mpls-enable {
            type enumeration {
              enum enable {
                value 2;
              }
              enum disable {
                value 3;
              }
            }
          }
        }

        list lsp-password {
          key "level";
          description "Configuration of metric style in LSPs";
          leaf level {
            type Isis-internal-level;
            description "Level to which configuration applies";
          }
          leaf algorithm {
            type Isis-authentication-algorithm;
            mandatory true;
            description "Algorithm";
          }
          leaf auth-type {
            type Isis-authentication-type;
            mandatory true;
            description "auth-type";
          }
          leaf password {
            type string{
              length "0..255";
            }
            mandatory true;
            description "Password";
          }
          leaf keychain-name {
            type string {
              length "0..32";
            }
            description "unencrypted Key Chain name";
          }
          leaf snp-enable {
            type Isis-auth-snp-lsp;
            description "whether enable snp or not";
          }
        }

        list spf-interval{
          key "level";
          description "ISIS spf calculation interval configuration";
          leaf level{     
            type Isis-internal-level;
            description "Level to which configuration applies";
          }
          leaf maximum-wait{
            type uint32{
              range "0..2147483647";
            }
            default "50000";
            units "milliseconds";
            description "Maximum wait before running a route calculation in milliseconds";
          }
          leaf minimum-wait{
            type uint32{
              range "0..2147483647";
            }
            default "500";
            units "milliseconds";
            description "Minimum wait before running a route calculation in milliseconds";
          }
          leaf initial-wait{
            type uint32{
              range "0..2147483647";
            }
            default "500";
            units "milliseconds";
            description "Initial wait before running a route calculation in milliseconds";
          }
        }

        list lsp-gen-interval {
          key "level";
          description "generate interval  of lsp with same lsp-id";
          leaf level {
            type Isis-internal-level;
            description "Level to which configuration applies";
          }
          leaf interval {
            type uint32{
              range "0..120";
            }
            default "30";
            units "seconds";
          }
        }

        container lsp-refresh-interval {
          description "Interval between re-flooding of unchanged LSPs";
          leaf interval {
            type uint32 {
              range "1..65235";
            }
            default "900";
            units "second";
            description "Seconds";
          }
        }

        container srgb {
          presence "Indicates a srgb node is configured.";
          description "Segment Routing Global Block configuration";
          leaf lower-bound {
            type uint32 {
              range "16..1048575";
            }
            description "The lower bound of the SRGB";
          }
          leaf upper-bound {
            type uint32 {
              range "16..1048575";
            }
            description "The upper bound of the SRGB";
          }
        }

        list bgp-ls {
          key "level";         
          leaf level {
            type  Isis-internal-level;
            description "Level to which configuration applies";
          }
          leaf bgp_ls_enable {
            type co-type:is-enable;
            description "enable or disable";
          }
        }

        container frr-use-cand-onlies  {
         description "FRR use candidate only configuration";         

          leaf ti-lfa-node-protect{
            type co-type:is-enable;
          }
        }

        container cspf-and-te {
          description "ISIS CSPF configuration. CSPF is belong to ISIS in  Nanjing ,
          there is no need to configure the CSPF-id";

          leaf te-to-level {
            type Isis-internal-level;
          }
        }

        container hostname{
          leaf dynamic-host-name {
            type Isis-hostname-enable;
            description
              "FALSE :0 will not display host-name
              If TRUE, dynamic hostname resolution is
              disabled, and system IDs will always be
              displayed by show and debug output.";
          }
          leaf host-name {
            type string {
              length "0..256";
            }
            description "Host name of device";
          }
        }

        container overload-bit{
          leaf interval {
            type uint32{
              range "5..86400";
            }
            default "600";
            units "seconds";
          }
        }
        
        list gr-sync {
          description "T2 time";
          key "level";
          leaf level {
            type Isis-internal-level;
          }
          leaf sync-timer {
            type uint16 {
              range "5..65535";
            }
            default "60";
            units "seconds";
          }
        }

        list af {
          key "af-name saf-name";
          description
            "Configuration for an IS-IS address-family. If
            a named (non-default) topology is being
            created it must be multicast.";
          leaf af-name {
            type  Isis-address-family;
            description "Address family MUST-CONFIG";
          }
          leaf saf-name {
            type  Isis-sub-address-family;
            description "Sub address family MUST-CONFIG";
          }

          container af-data {
            presence "Indicates a af-data node is configured.";
            description "Data container.";

            container summary-prefixes {
              description "Summary-prefix configuration.unused.";
              list propagation {
                key "source-destination-level";
                description "Propagate routes between IS-IS levels";                
                leaf source-destination-level {
                  type  Isis-level-to-level;
                  description "Destination level for routes.  Must differ from SourceLevel";
                }
                leaf access-list-name {
                  type Isis-access-list-type;
                  description "Access-list limiting routes to be propagated";
                }
              }
            }

            list redistribution {
              key "protocol-name protocol-instance-id protocol-instance-name";
              description "Redistribution of other protocols into this IS-IS instance";
              leaf protocol-name {
                type Isis-redist-proto;
                description
                  "The protocol to be redistributed.  OSPFv3
                  may not be specified for an IPv4 topology
                  and OSPF may not be specified for an IPv6 topology.";
              }                
              leaf protocol-instance-id {
                must "(../protocol-name='ospf' and ../protocol-instance-id>0 and ../protocol-instance-id<65536) 
                      or (../protocol-name='ospfv3' and ../protocol-instance-id>0 and ../protocol-instance-id<65536) 
                      or (../protocol-name='bgp' and ../protocol-instance-id=0) 
                      or (../protocol-name='connected' and ../protocol-instance-id=0) 
                      or (../protocol-name='static' and ../protocol-instance-id=0)
                      or (../protocol-name='rip' and ../protocol-instance-id=0)
                      or (../protocol-name='isis-sr-local' and ../protocol-instance-id=0)
                      or (../protocol-name='isis' and ../protocol-instance-id=0)";
                type uint32 {
                  range 0..65535;
                }
                description
                  "Protocol Instance Identifier.  Mandatory
                  for OSPF and BGP application, must not
                  be specified otherwise.";
              }
              leaf protocol-instance-name {
                must "(../protocol-name='isis')
                      or (../protocol-name='isis-sr-local')
                      or (../protocol-name='rip' and ../protocol-instance-name='nil') 
                      or (../protocol-name='bgp' and ../protocol-instance-name='nil') 
                      or (../protocol-name='connected' and ../protocol-instance-name='nil') 
                      or (../protocol-name='static' and ../protocol-instance-name='nil') 
                      or (../protocol-name='ospf' and ../protocol-instance-name='nil')
                      or (../protocol-name='ospfv3' and ../protocol-instance-name='nil')";
                type isis-redistribute-instance-name;
                description
                  "Protocol Instance Identifier.  Mandatory
                  for ISIS and application, must not
                  be specified otherwise.";
              }
              leaf metric {
                type uint32 {
                  range "0..16777215";
                }
                description "Metric for redistributed routes: <0-63> for narrow, <0-16777215> for wide";
              }
              leaf metric-type {
                type Isis-metric;
                description "IS-IS metric type";
              }
              leaf levels {
                type Isis-configurable-levels;
                default "level2";
                description "Levels to redistribute routes into";
              }
              container route-policy {
                leaf config {
                  type co-type:is-enable; 
                }
                leaf route-policy-name {
                  type Isis-route-policy-ref;
                  description "Route policy to control redistribution.";
                }
              }
            }

            container mpls-te-router-id {
              description
              "MPLS configuration. MPLS configuration will
              only be applied for the IPv4-unicast address-family.";                
              leaf router-id{
                description "Traffic Engineering stable IP address for system";
                type inet:ip-address-no-zone;  
              }
            }

            container default-route {
              leaf always {
                type co-type:is-enable;
              }
            }

            leaf adjacency-check {
              type  Isis-adjacency-check-state;
            }

            list af-distance{
              key "sys-id";
              leaf value{
                type uint16{
                  range "1..255";
                }
                default "115"; 
              }
              leaf sys-id{
                type string{
                  length "0..15";                               
                }          
              }
            }
      
            list multi-topology {
              key "level";
              description "Configuration of metric style in LSPs";
              leaf level {
                type Isis-internal-level;
                description "Level to which configuration applies";
              }
              leaf enable{
                type co-type:is-enable;
                description "open the advertise-local switch";
              }
            }

            list af-summary{
              description "Create aggregate addresses for the ISIS protocol";
              key "ipv4-prefix";
              leaf ipv4-prefix{
                type inet:ipv4-prefix;
                must " ( ../../../af-name = 'ipv4')" ;
              }
              leaf metric{
                type uint32{
                  range "1..63";
                }
              }
              leaf level{
                type Isis-configurable-levels;
              }
            }
          } /*end container af-data*/  
        } /*end list af*/

        container isis-interfaces { 
          description "Per-interface configuration";

          list isis-interface {
            key "interface-name";  
            description "Configuration for an IS-IS interface";

            leaf interface-name {
              type Isis-if-ref;
              description "Interface name MUST-CONFIG";
            }

            leaf circuit-type {
              type Isis-configurable-levels;
              description "Configure circuit type for interface";
            }

            leaf network-type {
              type  Isis-network-type;
              description "IS-IS will attempt to form point-to-point
                over LAN adjacencies over this interface.";
            }
            
            
            list csnp-interval {
              key "level";
              description "csnp send interval";
              leaf level {
                type Isis-internal-level;
                description "Level to which configuration applies";
              }
              leaf interval {
                type uint16{
                  range "1..65535";
                }
                default "10";
                units "seconds";
              }
            }

            container retransmit-lsp-interval {
              leaf interval {
                type uint16{
                  range "1..65535";
                }
                default "5";
                units "seconds";
              }
            }

            container min-lsp-interval {
              leaf interval {
                type uint16{
                  range "1..65535";
                }
                default "33";
                units "milliseconds";
              }
            }

            list priority {
              key "level";
              description "DIS-election priority";
              leaf level {
                type  Isis-internal-level;
                description "Level to which configuration applies";
              }
              leaf priority-value {
                type uint32 {
                  range "0..127";
                }
                default "64";
                description "Priority";
              }
            }

            container interface-frr-table{
              description "Fast-ReRoute configuration";

              leaf ti-lfa{
                type co-type:is-enable;
              }

            }

            list narrow-metric {
              key "level";
              description
              "Metric configuration. Legal value depends on
              the metric-style specified for the topology. If
              the metric-style defined is narrow, then only a
              value between <1-63> is allowed and if the
              metric-style is defined as wide, then a value
              between <1-16777215> is allowed as the metric
              value.  All routers exclude links with the
              maximum wide metric (16777215) from their SPF ";
              leaf level {
                type  Isis-internal-level;
                description "Level to which configuration applies";
              }
              leaf metric {
                type uint32 {
                  range "1..63";
                }
                mandatory true;
                description "Allowed metric: <1-63> for narrow";
              }
            }

            list wide-metric {
              key "level";
              description
              "Metric configuration. Legal value depends on
              the metric-style specified for the topology. If
              the metric-style defined is narrow, then only a
              value between <1-63> is allowed and if the
              metric-style is defined as wide, then a value
              between <1-16777215> is allowed as the metric
              value.  All routers exclude links with the
              maximum wide metric (16777215) from their SPF  ";
              leaf level {
                type  Isis-internal-level;
                description "Level to which configuration applies";
              }
              leaf metric {
                type union {
                  type enumeration {
                    enum maximum {
                      value 16777215;
                      description
                     "Maximum wide metric.  All routers will
                      exclude this link from their SPF";
                    }
                  }
                  type uint32 {
                    range "1..16777215";
                  }
                }
                mandatory true;
                description "Allowed metric:  <1-16777215> for wide";
              }
            }


            list hello-password {
              key "level";
              description
              "IIH passwords. This must exist if a
              HelloAcceptPassword of the same level exists.";               
              leaf level {
                type  Isis-internal-level;
                description "Level to which configuration applies";
              }              
              leaf algorithm {
                type Isis-authentication-algorithm;
                mandatory true;
                description "Algorithm";
              }
              leaf auth-type {
                type Isis-authentication-type;
                mandatory true;
                description "auth-type";
              }
              leaf password {
                type string{
                  length "0..255";
                }
                mandatory true;
                description "Password or unencrypted Key Chain name";
              }                       
              leaf keychain-name {
                type string {
                   length "0..32";
                }
              }
            }

            leaf padding-type {
              type Isis-hello-padding;
              description "Hello padding type value";
            }

            list hello-multiplier {
              key "level";
              description
                "Hello-multiplier configuration. The number
                of successive IIHs that may be missed on an
                adjacency before it is considered down.";
              leaf level {
                type  Isis-internal-level;
                description "Level to which configuration applies";
              }
              leaf multiplier {
                type uint32 {
                  range "2..100";
                }
                default "3";
                description "Hello multiplier value";
              }
            }

            list hello-interval {
              key "level";
              description
                "Hello-interval configuration. The interval
                at which IIH packets will be sent. This
                will be three times quicker on a LAN
                interface which has been electted DIS.";
              leaf level {
                type  Isis-internal-level;
                description "Level to which configuration applies";
              }             
              leaf interval {
                type uint32 {
                  range "3..65535";
                }
                units "second";
                mandatory true;
                description "Seconds";
              }
            }

            list gr-hello{
              description "T1 time";
              key "level";
              leaf level {
                type Isis-internal-level;
              }
              leaf hello-interval{
                type uint16 {
                  range "1..65535";
                }
                default "3";
                units "seconds";
              }
            }
            
            list interface-af {
              key "af-name saf-name";
              description
                "Configuration for an IS-IS address-family
                on a single interface. If a named
                (non-default) topology is being created it
                must be multicast. Also the topology ID
                mustbe set first and delete last in the
                router configuration.";

              leaf af-name {
                type Isis-address-family;
                description "Address family MUST-CONFIG";
              }
              leaf saf-name {
                type Isis-sub-address-family;
                description "Sub address family MUST-CONFIG";
              }

              container prefix-sids{
                 description "Assign prefix SID to an interface, 
                    ISISPHPFlag will be rejected if set to disable, 
                    ISISEXPLICITNULLFlag will override the value of 
                    ISISPHPFlag";
                leaf type{
                  type  Isis-sid-type;
                  description "SID type for the interface, index-SID as an index, 
                      absolute-SID as an absolute label";
                }
                leaf absolute-id{
                  type uint32{
                  range "16..1048575";
                  }
                  //mandatory true;
                  description 
                  "The absolute label value for the interface .absolute-id must be in
                  the range of srgb in isis process or the range of srgb in segmentrouting
                  srgb.preference is srgb in isis process.lower-bound<=absolute-id and
                  upper-bound>=absolute-id";
                }                            
                leaf index-id{
                  type uint32{
                    range "0..1048560";
                  }
                  //mandatory true;
                  description 
                  "The relative ID value for the interface. index-id must be in the
                  range of srgb in isis process or the range of srgb in segmentrouting
                  srgb,preference is srgb in isis process.upper-bound - lower-bound >= index-id";
                }                
                leaf php{
                  type Isisphp-flag;
                  default "enable";
                  description "Enable/Disable Penultimate Hop Popping";
                }
                leaf nflag-clear{
                  type co-type:is-enable;
                  description "Clear N-flag for the prefix-SID";
                }
                leaf explicit-null{
                  type co-type:is-enable;
                  description "Enable/Disable Explicit-null";
                }
                must "not (php = 'enable' and  explicit-null = 'enable')" {
                  error-message "you cannot enable explicit-null and php at the same time";
                }
              }
            } /* end list interface-af */
          } /* end container interface */
        } /* end container interfaces */
      } /* end list isis-instance */
    } /* end container isis-instances */


  
    container static-adj {
      description "Isis use this range for list adj-sids.
      The matched nbr will use the static label to replace the dynamic.";       
      container sid-range {           
        leaf lower-bound {
          type uint32 {
            range "16..1048575";
          }
        }
        leaf upper-bound {
          type uint32 {
            range "16..1048575";
          }
        }
      }

      list adj-sids {
        key "adj-sid";        
        leaf adj-sid {
          type uint32{
            range "16..1048575";
          }
          description "adjacency sid ,must in the range of sid-range.
          must (../../sid-range/lower-bound<=../adjacency-sid and ../../sid-range/upper-bound>=../adjacency-sid)";
        }         
        leaf local-ip {
          type inet:ipv4-address-no-zone;
        }
        leaf remote-ip {
          type inet:ipv4-address-no-zone;
        }
        leaf backup {
          type boolean;
          description "true: support backup function, set Backup Flag in Packet.";
        }
      }
    }
    container graceful-restart {
      description "GR enable and T3 time";
      leaf gr-flag {
        description "Enable restarter and helper functions";
        type co-type:is-enable;
      }

      leaf gr-period-timer {
        description "T3 time";
        type uint16 {
          range "1..65535";
        }
        default "65535";
        units "seconds";
      }
    }
  } /* end container isis */
}
