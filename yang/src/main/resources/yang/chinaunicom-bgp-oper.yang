module chinaunicom-bgp-oper {
  /*** NAMESPACE / PREFIX DEFINITION ***/

  namespace "http://chinaunicom.com/yang/ipprotocol/routing/chinaunicom-bgp-oper";


  prefix "bgp-oper";

  /*** LINKAGE (IMPORTS / INCLUDES) ***/


  import chinaunicom-bgp { prefix "bgp"; }

  import ietf-inet-types { prefix "inet"; }
  
  import chinaunicom-datatype-common { prefix "co-type"; }
  


  /*** META INFORMATION ***/

  organization "Fiberhome Systems, Inc.";

  contact
    "Fiberhome Systems, Inc.
     
		Postcode: 430073 
		Address: No.6,Gaoxin 4 Rd,Donghu Hi-Tech Development Zone, Wuhan, Hubei
		Tel: +XXXXXXXXXXXX

		E-mail: yang- author@fiberhome.com";


  description 
    "This module contains a collection of YANG definitions
     for Fiberhome bgp package configuration.

     This module contains definitions
     for the following management objects:
       bgp: IS-IS state for all instances


     Copyright (c) 2013-2016 by Fiberhome Systems, Inc.
     All rights reserved.";

  revision "2019-09-03" {
    description
      "Initial version";
  }
  
    typedef bgp-neighbor-caps-type {
	  type enumeration {
		enum address-family-ipv4-unicast {
			value 1;
			description "address-family-ipv4-unicast";
		}
		enum address-family-ipv4-multicast {
			value 2;
			description "address-family-ipv4-multicast";
		}
		enum address-family-vpnv4-unicast {
			value 3;
			description "address-family-vpnv4-unicast";
		}
		enum address-family-ipv4-labeled {
			value 4;
			description "address-family-ipv4-labeled";
		}
		enum address-family-ipv6-unicast {
			value 5;
			description "address-family-ipv6-unicast";
		}
		enum address-family-ipv6-multicast {
			value 6;
			description "address-family-ipv6-multicast";
		}
		enum address-family-vpnv6-unicast {
			value 7;
			description "address-family-vpnv6-unicast";
		}
		enum address-family-ipv6-labeled {
			value 8;
			description "address-family-ipv6-labeled";
		}
		enum route-refresh {
			value 9;
			description "route-refresh";
		}
		enum graceful-restart {
			value 10;
			description "graceful-restart";
		}
		enum address-family-l2vpn-evpn {
			value 11;
			description "address-family-l2vpn-evpn";
		}
		enum address-family-ls-publs {
			value 12;
			description "address-family-ls-publs";
		}
	  }
    }
  
	typedef bgp-neighbor-capability {
	  type enumeration {
		enum advertised  {
			value 1;
			description "capability advertised";
		}
		enum received  {
			value 2;
			description "capability received";
		}
		enum advertised-received  {
			value 3;
			description  "capability advertised and received";
		}
	  }	
	}
	
	typedef bgp-neighbor-state {
	  type enumeration {
		enum bgp_idle {
			value 1;
			description "BGP state idle";
		}
		enum bgp_connect {
			value 2;
			description "BGP state connect";
		}
		enum bgp_active {
			value 3;
			description "BGP state active";
		}
		enum bgp_opensent {
			value 4;
			description "BGP state opensent";
		}
		enum bgp_openconfirm {
			value 5;
			description "BGP state openconfirm";
		}
		enum bgp_established {
			value 6;
			description "BGP state established";
		}
	  }
	}
  
  	typedef bgp-ls-type {
	  type enumeration {
		enum node {
			value 1;
			description "BGP-LS node";
		}
		enum link {
			value 2;
			description "BGP-LS link";
		}
		enum prefix {
			value 3;
			description "BGP-LS prefix";
		}
	  }
	}
	
  container bgp-oper {
	config false;
	description "BGP operational data";
	
	container bgp-neighbors{
		description "BGP neighbors";
		container bgp-neighbor-capabilities {
		
			list bgp-neighbor-capability {
				description "bgp instance operational data";
				
									
				leaf peer-ipv4-addr {
					type inet:ipv4-address;
				}
				leaf peer-ipv6-addr {
					type inet:ipv6-address;
				}
				leaf caps-type {
					type bgp-neighbor-caps-type;
				}
				leaf capability {
					type bgp-neighbor-capability;
				}
				leaf state {
					type bgp-neighbor-state;
				}
				leaf instance-id {
					type inet:as-number;
				}
				leaf vrf-name {
					type co-type:vpn-name-with-global;
				}
			}
		}
		
	}
	
	container bgp-routes{
		description "bgp routes";
		
		container bgp-ls-routes{
			list bgp-ls-route {
				description "show bgp-ls summary";
				
				key "ls-buf";
				
				leaf afi {
					type bgp:Bgp-address-family;
				}
				leaf safi {
					type bgp:Bgp-ls-sub-address-family;
				}
				leaf ls-buf {
					type string{
						length 1..1024 ;
					}
				}
				leaf detail {
					type co-type:is-enable;
				}
				leaf ls-type {
					type bgp-ls-type;
				}
			}
		}
	}	
	 
  }

}
