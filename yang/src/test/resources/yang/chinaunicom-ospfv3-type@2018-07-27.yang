module chinaunicom-ospfv3-type {

    /*** NAMESPACE / PREFIX DEFINITION ***/

	namespace "http://chinaunicom.com/yang/datatype/chinaunicom-ospfv3-type";

	prefix "ospfv3-type";
	
	import chinaunicom-interface-common{	revision-date 2020-12-31;prefix "if";}
	
    /*** LINKAGE (IMPORTS / INCLUDES) ***/
    
    organization "Fiberhome Systems, Inc.";

    contact
    "Fiberhome Communications Techlonogy Co., Ltd.
     
      Postcode: 430073
      Address: No.6,Gaoxin 4 Rd,Donghu Hi-Tech Development Zone, Wuhan, Hubei
     
      E-mail: yang- author@fiberhome.com";

    description
    "This module contains a collection of YANG definitions
      for Fiberhome  ospfv3 package configuration.
     
      This module contains definitions
      for the following management objects:
        ospfv3:  configuration
     
      Copyright (c) 2013-2020 by Fiberhome Systems, Inc.
      All rights reserved.";

    revision 2018-07-27 {
    description
		"Initial version.";
    } 
    
	typedef if-name-ref{
		type union {
		type if:ethphy-name;
		type if:ethvir-name;
		type if:ethlag-name;
		type if:veth-name;
		type if:flexetunnel-name;
		type if:tunnel-name;
		type if:lb-name;
		type if:mgmt-name;
		type if:ethsub-name;
		type if:dcn-name;
		type if:wlan-name;
        type if:lte-name;		
		}
	} 
	
	typedef redistribute-instance-name{
		type union {
			type string{
				length "1..32";
				}
			type string {
				pattern "nil";
			}
		}
	}  	

    typedef import-route-protocol{
		type enumeration {
			enum connect   {
				value 1;
				description "connect ";
			}
			enum static {
				value 2;
				description "static";
			}
			enum bgp {
				value 3;
				description "bgp";
			}
			enum ospf {
				value 4;
				description "ospf";
			}
			enum isis {
				value 5;
				description "isis";
			}
		}
	}  

	typedef translator-role{
		type enumeration {
			enum candidate {
				value 1;
				description "candidate";
			}
			enum always {
				value 2;
				description "always";
			}
		}
	} 
	
    typedef metric-type{
		type enumeration {
			enum Type1 {
				value 1;
				description "Type1";
			}
			enum Type2 {
				value 2;
				description "Type2";
			}

		}
	}  

    typedef ospf-area-type{
		type enumeration {
			enum normal {
				value 1;
				description "normal";
			}
			enum stub {
				value 2;
				description "stub";
			}
			enum nssa {
				value 3;
				description "nssa";
			}
		}
	}  

    typedef network-type{
		type enumeration {
			enum broadcast {
				value 1;
				description "broadcast";
			}
			enum non-broadcast   {
				value 2;
				description "non broadcast";
			}
			enum point-to-point  {
				value 3;
				description "point to point";
			}
			enum point-to-multipoin {
				value 4;
				description "point to multipoin";
			}
		}
	} 
 
}
