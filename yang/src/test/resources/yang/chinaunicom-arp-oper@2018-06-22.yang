module chinaunicom-arp-oper {

  /*** NAMESPACE / PREFIX DEFINITION ***/
  namespace "http://chinaunicom.com/yang/ipservice/chinaunicom-arp-oper";
  prefix "arp-oper";

  /*** LINKAGE (IMPORTS / INCLUDES) ***/
  import ietf-yang-types {	revision-date 2013-07-15; prefix "yang"; }
  import ietf-inet-types {	revision-date 2013-07-15; prefix "inet"; }
  import chinaunicom-datatype-common {	revision-date 2020-08-14; prefix "co-type"; }
  import chinaunicom-arp {	revision-date 2017-08-26; prefix "arp"; }

  organization "Fiberhome Systems, Inc.";

  contact
    "Fiberhome Communications Techlonogy Co., Ltd.

     Postcode: 430073
     Address: No.6,Gaoxin 4 Rd,Donghu Hi-Tech Development Zone, Wuhan, Hubei

     E-mail: ykou@fiberhome.com";

  description
    "This module contains a collection of YANG definitions
     for Fiberhome chinaunicom-V5 arp-oper package operational data.

     Copyright (c) 2013-2016 by Fiberhome Systems, Inc.
     All rights reserved.";

  revision 2018-06-22 {
    description "Initial version.";
  }

  /* typedefs */
  typedef arp-type-enum {
    type enumeration {
      enum dynamic      { value 1; }
      enum static       { value 2; }
      enum interface    { value 3; }
      enum vrrp         { value 4; }
      enum incompleted  { value 5; }
      enum bdif         { value 6; }
    }
  }

  container arp-oper {
    config false;

    container arp-items {
      list arp-item {

        leaf vrf-name {
          description "The vrf-name of this item.";
          type co-type:vpn-name-with-global;
        }

        leaf ip-addr {
          description "The ip-addr of this item.";
          type inet:ipv4-address;
        }

        leaf mac-addr {
          description "The mac-addr of this item.";
          type yang:mac-address;
        }

        leaf arp-type {
          description "The arp-type of this item.";
          type arp-oper:arp-type-enum;
        }

        leaf expire-time {
          description "The expire-time of this item.";
          type uint32;
        }

        leaf if-name {
          description "The if-name of this item.";
          type arp:if-ref;
        }

        leaf svlan-id {
          description "The svlan-id of this item.";
          type uint16;
        }

        leaf cvlan-id {
          description "The cvlan-id of this item.";
          type uint16;
        }
      }
    }

    container arp-summary {

      leaf incomp-count {
        description "The count of Incompleted items.";
        type uint32;
      }

      leaf dynamic-count {
        description "The count of Dynamic items.";
        type uint32;
      }

      leaf static-count {
        description "The count of Static items.";
        type uint32;
      }

      leaf if-count {
        description "The count of Interface items.";
        type uint32;
      }

      leaf vrrp-count {
        description "The count of VRRP items.";
        type uint32;
      }

      leaf bdif-count {
        description "The count of BDIF items.";
        type uint32;
      }

      leaf total {
        description "The count of Total items.";
        type uint32;
      }
    }

    container arp-conflicts {
      list arp-conflict {
        key "if-name ip-addr";

        leaf if-name {
          description "The if-name of this item.";
          type arp:if-ref;
        }

        leaf ip-addr {
          description "The ip-addr of this item.";
          type inet:ipv4-address;
        }

        leaf local-mac {
          description "The local-mac of this item.";
          type yang:mac-address;
        }

        leaf peer-mac {
          description "The mpeer-mac of other item.";
          type yang:mac-address;
        }

        leaf svlan {
          description "The svlan of this item.";
          type uint16;
        }

        leaf cvlan {
          description "The cvlan of this item.";
          type uint16;
        }
      }
    }

    container arp-if-summarys {
      list arp-if-summary {
        key "if-name";

        leaf if-name {
          description "The name of the interface.";
          type arp:if-ref;
        }

        leaf incomp-count {
          description "The count of Incompleted items at the interface.";
          type uint32;
        }

        leaf dynamic-count {
          description "The count of Dynamic items at the interface.";
          type uint32;
        }

        leaf static-count {
          description "The count of Static items at the interface.";
          type uint32;
        }

        leaf if-count {
          description "The count of Interface items at the interface.";
          type uint32;
        }

        leaf vrrp-count {
          description "The count of VRRP items at the interface.";
          type uint32;
        }

        leaf bdif-count {
          description "The count of BDIF items at the interface.";
          type uint32;
        }

        leaf total {
          description "The count of Total items at the interface.";
          type uint32;
        }
      }
    }

    container arp-if-packet-statistics {
      list arp-if-packet-statistic {
        key "if-name";

        leaf if-name {
          description "The name of the interface.";
          type arp:if-ref;
        }

        leaf req-out-count {
          description "The count of ARP-Request messages sent out of the interface.";
          type uint32;
        }

        leaf reply-in-count {
          description "The count of ARP-Reply messages received from the interface.";
          type uint32;
        }

        leaf req-in-count {
          description "The count of ARP-Request messages received from the interface.";
          type uint32;
        }

        leaf reply-out-count {
          description "The count of ARP-Reply messages sent out of the interface.";
          type uint32;
        }

        leaf miss-count {
          description "The count of ARP-Miss messages received from the interface.";
          type uint32;
        }

        leaf error-in-count {
          description "The count of error messages received from the interface.";
          type uint32;
        }
      }
    }
  }
  
  rpc arp-items-summary {

    input{

      leaf vrf-name {
        description "The vrf-name of this query.";
        type co-type:vpn-name-with-global;
      }

      leaf if-name {
        description "The if-name of this query.";
        type arp:if-ref;
      }
    }
  
    output{
    
      leaf total-count {
        description "The count of this query.";
        type uint32;
      }
    }  
  }

  rpc arp-items-clear {
    input {

      leaf if-name {
        description "The name of the interface.";
        type arp:if-ref;
      }
    }
  }

}
