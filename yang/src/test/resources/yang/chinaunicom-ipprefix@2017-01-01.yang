module chinaunicom-ipprefix {

  /*** NAMESPACE / PREFIX DEFINITION ***/
	
  namespace "http://chinaunicom.com/yang/ipprotocol/chinaunicom-ipprefix";
	
  prefix "ipprefix";

  /*** LINKAGE (IMPORTS / INCLUDES) ***/

  import ietf-inet-types {	revision-date 2013-07-15; prefix "inet"; }
  

  /*** META INFORMATION ***/

  organization "Fiberhome Systems, Inc.";

  contact
    "Fiberhome Systems, Inc.
     
		Postcode: 430073 
		Address: No.6,Gaoxin 4 Rd,Donghu Hi-Tech Development Zone, Wuhan, Hubei
		Tel: +XXXXXXXXXXXX

		E-mail: yang- author@fiberhome.com";


  description 
    "This module contains a collection of YANG definitions
     for Fiberhome chinaunicom-R8000 rpl package configuration.

     This module contains definitions
     for the following management objects:
       rpl: rpl configuration for all instances

     This YANG module augments the
       FH-chinaunicom-R8000-snmp-agent-cfg
     module with configuration data.

     Copyright (c) 2013-2016 by Fiberhome Systems, Inc.
     All rights reserved.";

  revision "2017-01-01" {
    description
      "chinaunicom R8000 6.0 revision.";
  }
 
 
  typedef list-name {
	  type string {
	    length "1..63";
	  }
  }
  
  typedef ipprefix-mode{
    type enumeration {
	  enum permit {
	    value 2;
	  }
	  enum deny {
	    value 3;
	  }
	}
  }
  
  typedef ipprefix-type{
    type enumeration {
      enum any {
        value 2;
      }
      enum prefix {
	    value 3;
        description "match rules by prefix name";
      }
    }
  }
  
  container ipprefix {
    container ip-prefix-list {
       description "name / label of the prefix set -- this is used to
                                reference the set in match conditions";
	 
	 list ipv4-prefix{ 
		 key "ipv4-prefix-name";
		 
		 leaf ipv4-prefix-name {
		   type ipprefix:list-name;
		 }
		 
		 list ipv4-prefix-node {
		   key "seq";
		   
		   leaf seq {
		     type uint32{
		       range "1..4294967295";
		     }
		   }
		 
		   leaf operation {
		     type ipprefix-mode;
		   }
		   leaf ge {
		     type uint16{
		       range "1..32";
		     }
		   }
		   leaf le {
		     type uint16{
		       range "1..32";
		      }
		   }
		   leaf ipv4-prefix {
		     type inet:ipv4-prefix;
		   }
		   leaf prefix-type {
		     type ipprefix-type;
		   }
		 }	 
	 }
	 
	 list ipv6-prefix{	
		 key "ipv6-prefix-name";
		 
		 leaf ipv6-prefix-name {
		   type ipprefix:list-name;
		 }
		 
		 list ipv6-prefix-node {
		   key "seq";
		 
		   leaf seq {
		     type uint32{
		       range "1..4294967295";
		      }
		   }
		 
		   leaf operation {
		     type ipprefix-mode;
		   }
		   leaf ge {
		     type uint16{
		       range "1..128";
		      }
		   }
		   leaf le {
		     type uint16{
		       range "1..128";
		      }
		   }
		 
		   leaf ipv6-prefix {
		     type inet:ipv6-prefix;
		   }
		   leaf prefix-type {
		     type ipprefix-type;
		   }
		 }
	  }
    }
  }
}
