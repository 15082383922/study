module chinaunicom-ipfrr-oper{

  /*** NAMESPACE / PREFIX DEFINITION ***/

  namespace "http://chinaunicom.com/yang/ipprotocol/routing/chinaunicom-ipfrr-oper";

  prefix "ipfrr-oper";

  /*** LINKAGE (IMPORTS / INCLUDES) ***/

  import ietf-inet-types {	revision-date 2013-07-15; prefix "inet"; }
  
  import chinaunicom-datatype-common {	revision-date 2020-08-14; prefix "co-type"; }
  
  import chinaunicom-interface-common{	revision-date 2020-12-31; prefix "if"; }
  
  import chinaunicom-protectgroup-common{	revision-date 2019-12-12; prefix "protgrp-co"; }
  
  import chinaunicom-ipfrr{	revision-date 2021-04-13; prefix "ipfrr"; }

  
  /*** META INFORMATION ***/

  organization "UTStarcom Telecom Co., Ltd.";

  contact
    "UTStarcom Telecom Co., Ltd.
     
     Postcode: 310053 
     Address: 368 Liuhe Road, Binjiang District,Hangzhou, Zhejiang

     E-mail: sheng.yu@utstar.com";

  description 
    "This module contains a collection of YANG definitions
     for Fiberhome chinaunicom ip frr protect info.

     This module contains definitions
     for the following management objects:
       ipfrr-oper

     Copyright (c) 2013-2021 by UTStarcom Telecom Co., Ltd.
     All rights reserved.";

  revision 2021-04-13{
      description 
        "First revision.";
  }

    typedef if-ref {
	    type union {
            type if:ethlag-name;
            type if:ethvir-name;
            type if:ethphy-name;
            type if:ethsub-name;
	        type if:veth-name;
            type if:ethlag-name;
            type if:flexetunnel-name;
	    }
    }
	
	/* GROUPINGS */
	grouping basic-state {
        leaf switch-state {
            type protgrp-co:lps-switch-state;
            description "switch state";
        }		  
	    leaf pri-path-state {	
            type protgrp-co:path-state;
            description "primary path state";
        }
		leaf bak-path-state {	
            type protgrp-co:path-state;
            description "backup path state";
        }
    }
	
	grouping detail-state {
		leaf revertive-mode{
			type protgrp-co:revertive-mode;
			description "revertive-mode";
		}
		leaf wtr-time{
			type uint32{
				range "0..30";
			}
			description "wtr-time";
		}
		leaf hold-off-time{
			type uint32{
				range "0..255";
			}
			description "hold off time";
		}
		leaf pri-if{
			type ipfrr-oper:if-ref;
			description "primary interface";
		}
		leaf bak-if{
			type ipfrr-oper:if-ref;
			description "backup interface";
		}
		leaf pri-alm-detect-mode{
			type protgrp-co:detect-mode;
			description "pri alarm detect mode";
		}
		leaf bak-alm-detect-mode{
			type protgrp-co:detect-mode;
			description "bak alarm detect mode";
		}
		leaf pri-detect-id{
			type uint32{
			  range "0..4294967295";
			}
			description "primary detect id";
		}
		leaf bak-detect-id{
			type uint32{
			  range "0..4294967295";
			}
			description "backup detect id";
		}
		leaf protect-entity-id{
			type uint32{
			  range "0..4294967295";
			}
			description "protect entity id";
		}
    }
	
	grouping hyfrr-detail-state {
		leaf revertive-mode{
			type protgrp-co:revertive-mode;
			description "revertive-mode";
		}
		leaf wtr-time{
			type uint32{
				range "0..30";
			}
			description "wtr-time";
		}
		leaf hold-off-time{
			type uint32{
				range "0..255";
			}
			description "hold off time";
		}
		leaf pri-if{
			type ipfrr-oper:if-ref;
			description "primary interface";
		}
		leaf bak-if{
			type ipfrr-oper:if-ref;
			description "backup interface";
		}
		leaf pri-tunnel-id{
			type uint32{
			    range "0..65535";
			}
			description "primary tunnel id";
		}
		leaf bak-tunnel-id{
			type uint32{
			    range "0..65535";
			}
			description "backup tunnel id";
		}
		leaf pri-alm-detect-mode{
			type protgrp-co:detect-mode;
			description "pri alarm detect mode";
		}
		leaf bak-alm-detect-mode{
			type protgrp-co:detect-mode;
			description "bak alarm detect mode";
		}
		leaf pri-detect-id{
			type uint32{
			  range "0..4294967295";
			}
			description "primary detect id";
		}
		leaf bak-detect-id{
			type uint32{
			  range "0..4294967295";
			}
			description "backup detect id";
		}
		leaf protect-entity-id{
			type uint32{
			  range "0..4294967295";
			}
			description "protect entity id";
		}
    }
	
    container ipfrr-oper{
	    config false;
	    description "ip frr oper container";
		
		container ipfrr-states{ 
		    description "ip frr protect states";
			
			/* IP-FRR SUM YANG Model */
			container ipfrr-sum {
			  description "ipfrr sum";
			  
			  leaf ipfrr-summary{
				type uint32{
				  range "0..4294967295";
				}
				description "ipfrr-summary";
			  }
			}
			
			list ipfrr-state{
				key "vrf-name pri-next-hop bak-next-hop";
				description "ip frr protect state list";
				
				leaf vrf-name{
					type ipfrr:vrf-ref;
					description "vpn instance name";
				}
					
				leaf pri-next-hop{
				    type inet:ip-address;
					description "primary next hop address";
				}
					
				leaf bak-next-hop{
				    type inet:ip-address;
				    description "backup next hop address";
				}
				  
                uses basic-state{
		        }
			}
			
			list ipfrr-detail-state{
				key "vrf-name pri-next-hop bak-next-hop";
				description "ip frr protect state list";
				
				leaf vrf-name{
					type ipfrr:vrf-ref;
					description "vpn instance name";
				}
					
				leaf pri-next-hop{
				    type inet:ip-address;
					description "primary next hop address";
				}
					
				leaf bak-next-hop{
				    type inet:ip-address;
				    description "backup next hop address";
				}
				  
                uses basic-state{
		        }
				
                uses detail-state{
		        }
			}
		}
		
		container hyfrr-states{ 
		    description "hyfrr protect states";
			
			/* MIX-FRR SUM YANG Model */
			container hyfrr-sum {
			  description "hyfrr sum";
			  
			  leaf hyfrr-summary{
				type uint32{
				  range "0..4294967295";
				}
				description "hyfrr-summary";
			  }
			}
			
			list hyfrr-state{
				key "vrf-name pri-next-hop bak-next-hop";
				description "hyfrr protect state list";
				
				leaf vrf-name{
					type co-type:vpn-name;
					description "vpn instance name";
				}
				
				leaf pri-next-hop{
				    type inet:ip-address;
					description "primary next hop address";
				}
				
				leaf bak-next-hop{
				    type inet:ip-address;
				    description "backup next hop address";
				}
				
                uses basic-state{
		        }
			}
			
			list hyfrr-detail-state{
				key "vrf-name pri-next-hop bak-next-hop";
				description "hyfrr protect state list";
				
				leaf vrf-name{
					type co-type:vpn-name;
					description "vpn instance name";
				}
				
				leaf pri-next-hop{
				    type inet:ip-address;
					description "primary next hop address";
				}
				
				leaf bak-next-hop{
				    type inet:ip-address;
				    description "backup next hop address";
				}
				
                uses basic-state{
		        }
				
                uses hyfrr-detail-state{
		        }
			}
		}
	}
	
	/* IP-FRR CMD RPC */
	rpc set-ipfrr-switch {
	  input {
		leaf vrf-name{
			type ipfrr:vrf-ref;
			description "vpn instance name";
		}
		leaf pri-next-hop{
			type inet:ip-address;
			description "primary next hop address";
		}
		leaf bak-next-hop{
			type inet:ip-address;
			description "backup next hop address";
		}
	    leaf switch-cmd-type{
		    type protgrp-co:lps-switch-cmd-type;
		    description "switch-cmd-type";
	    }
	  }
	}

	/* MIX-FRR CMD RPC */
	rpc set-hyfrr-switch {
	  input {
		leaf vrf-name{
			type co-type:vpn-name;
			description "vpn instance name";
		}
		leaf pri-next-hop{
			type inet:ip-address;
			description "primary next hop address";
		}
		leaf bak-next-hop{
			type inet:ip-address;
			description "backup next hop address";
		}
	    leaf switch-cmd-type{
		    type protgrp-co:lps-switch-cmd-type;
		    description "switch-cmd-type";
	    }
	  }
	}
}
