module chinaunicom-ipfrr {

    /*** NAMESPACE / PREFIX DEFINITION ***/

    namespace "http://chinaunicom.com/yang/ipprotocol/routing/chinaunicom-ipfrr";


    prefix "ipfrr";
  
    /*** LINKAGE (IMPORTS / INCLUDES) ***/

    import chinaunicom-l3vpn {	revision-date 2019-10-24; prefix "l3vpn"; }
    import chinaunicom-routemap {	revision-date 2019-12-30; prefix "routemap"; }
	import chinaunicom-datatype-common{
		prefix "co-type";
	revision-date 2020-08-14;
	}
    
  
    /*** META INFORMATION ***/

  /*** META INFORMATION ***/
  organization "UTStarcom Telecom Co., Ltd.";

  contact
    "UTStarcom Telecom Co., Ltd.
     
     Postcode: 310053 
     Address: 368 Liuhe Road, Binjiang District,Hangzhou, Zhejiang

     E-mail: sheng.yu@utstar.com";
     
    description 
    "This YANG module defines the ip frr configuration.

     Copyright (c) 2013-2021 by UTStarcom Telecom Co., Ltd.
     All rights reserved.";

  revision 2021-04-13{
      description 
        "First revision.";
  }
 
    typedef vrf-ref {
	 
		    type co-type:vpn-name;
	}
 
    typedef routemap-ref {
        type routemap:policy-name;   
    } 

  
    typedef af-type{
        type enumeration {
		    enum ipv4 {
		        value 1;
		        description "ipv4 address family.";
		   }
		    enum ipv6 {
		        value 2;
                description "ipv6 address family.";
            }
        }
    }
	 augment "/l3vpn:l3vpn/l3vpn:vpn-instances/l3vpn:vpn-instance/l3vpn:vpnInst" {
		
		container ip-frr {
			description "ip frr container"; 
			container ip-frr-route-policies {
				description "ip frr configuration data"; 
				container ip-frr-route-policy {					
						
					leaf route-policy {
						description
						"Specify ip-frr route-policy name.";
						type ipfrr:routemap-ref;
					} 
					
				}
				
				container hybrid-frr-route-policy {													
						
					leaf route-policy {
						description
						"Specify hybrid-frr route-policy name.";
						type ipfrr:routemap-ref;
					}
					
				}
			}
		}
		
	}
		
	
	
	
	
	container public-ip-frr {
			description "public ip frr container"; 
			container public-ip-frr-route-policies {
			   description "public ip frr configuration data"; 
				
					list ip-frr-route-policy {						
						key "af-mode";										
						leaf af-mode {							
							description "Specify address family."; 
							type ipfrr:af-type;
						}					
						leaf route-policy {							
							description
							"Specify ip-frr route-policy name.";
							type ipfrr:routemap-ref;
						} 
					}
				
						
					list hybrid-frr-route-policy {						
						key "af-mode";					
						leaf af-mode {								
								description "Specify address family."; 
								type ipfrr:af-type;
							}						
						leaf route-policy {								
								description
								"Specify ip-frr route-policy name.";
								type ipfrr:routemap-ref;
						} 
					}
					
			}
		}
	
	
	}
