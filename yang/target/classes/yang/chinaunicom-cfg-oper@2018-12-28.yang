module chinaunicom-cfg-oper {

  /*** NAMESPACE / PREFIX DEFINITION ***/

  namespace "http://chinaunicom.com/yang/basicmanage/chinaunicom-cfg-oper";


  prefix "cfg-oper";
  
  /*** META INFORMATION ***/

  organization "Fiberhome Systems, Inc.";

  contact
    "Fiberhome Systems, Inc.
     
		Postcode: 430073 
		Address: No.6,Gaoxin 4 Rd,Donghu Hi-Tech Development Zone, Wuhan, Hubei
		Tel: +XXXXXXXXXXXX

		E-mail: yang- author@fiberhome.com";

  description 
    "This module contains a collection of YANG definitions
     for Fiberhome chinaunicom basicmanage configuration.

     Copyright (c) 2013-2015 by Fiberhome Systems, Inc.
     All rights reserved.";

  revision "2018-12-28" 
  {
    description
      "Init revision.";
  }
	
	container cfg-oper {
		config false;
		description
		"config information.";
	
		container startup-file-state {
			description
				" configuration file.";
			leaf current {
				type string {
					length "1..64";
				}
				description
					"Current configuration startup file,When device-side current is empty, the returned string is 'NULL' ";
			}
			leaf next {
				type string {
					length "1..64";
				}
				description
					"Next time configure the startup file,When device-side next is empty, the returned string is 'NULL' ";
			}
		}
	}
	
	rpc save-cfg {
	  description
		"Save configuration file.";
	  input{
		  leaf filename {
			  type string {
				  length "1..64";
			    }
			    description
				  "Configuration files saved by the user.";
		    }
	    }
	}
	
	rpc set-startup-file {
	  description
		"Set configuration file.";
	  input {
		  leaf next {
			  type string {
				  length "1..64";
			    }
			    description
				  "Next time configure the startup file.";
		    }
	    }
	}
	  
}
