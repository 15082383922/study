module chinaunicom-dhcp {

  /*** NAMESPACE / PREFIX DEFINITION ***/

  namespace "http://chinaunicom.com/yang/systemmanage/chinaunicom-dhcp";

  prefix "dhcp";
  
  /*** LINKAGE (IMPORTS / INCLUDES) ***/
  //import ietf-yang-types {	revision-date 2013-07-15; prefix "yang"; }  
  import chinaunicom-interface-common {	revision-date 2020-12-31; prefix "if";}
  import chinaunicom-datatype-common {	revision-date 2020-08-14; prefix "co-type";}
  import ietf-inet-types {	revision-date 2013-07-15; prefix "inet"; }
  
  /*** META INFORMATION ***/
  organization "Fiberhome Systems, Inc.";

  contact
    "Fiberhome Communications Techlonogy Co., Ltd.
     
     Postcode: 430073 
     Address: No.6,Gaoxin 4 Rd,Donghu Hi-Tech Development Zone, Wuhan, Hubei

     E-mail: dhxiao@fiberhome.com";

  description
     "This module contains a collection of YANG definitions
     for Fiberhome chinaunicom-R8000 dhcp relay package configuration.

     This module contains definitions
     for the following management objects:
       dhcp4-global-cfg: dhcp4 Global scoped configuration
	   dhcp6-global-cfg: dhcp6 Global scoped configuration
       profile4-relays: dhcpv4 relay configuration
       dhcp4-interfaces: dhcpv4 interface configuration,incluce relay server snooping
       profile6-relays: dhcpv6 relay configuration
       dhcp6-interfaces: dhcpv6 interface configuration,incluce relay server
       dhcp4-client: dhcpv4 client interface configuration
       
     Copyright (c) 2013-2015 by Fiberhome Systems, Inc.
     All rights reserved.";
	 
  revision 2019-09-24 {
    description
     "dhcp support bdif wlan lte.dhcp support option82-remote-id.";
  }
  
  revision 2018-03-27 {
    description
     "Initial version.";
  }

  // typedef statements
  
	typedef if-ref {
		type union {
			type if:ethphy-name;
			type if:ethvir-name;
			type if:ethlag-name;
			type if:veth-name;
			type if:ethsub-name;
			type if:flexetunnel-name;
			type if:mgmt-name;
			type if:tunnel-name;
			type if:vcg-name;
			type if:bdif-name;
			type if:wlan-name;
			type if:lte-name;
		}
	}
    
  typedef snooping-trust {
    type enumeration {
      enum disable {
		    value 0;
        description
          "dhcp snooping, Snooping-trust disable";
      }
      enum enable {
		    value 1;
        description
          "dhcp snooping, Snooping-trust enable";
      }
    }
    description
      "dhcp snooping, Describes the snooping-trust switch, disable or enable";
  }
  
  typedef dhcp-enable {
    type enumeration {
      enum disable {
        value 0;
        description
          "dhcp disable";
      }
      enum enable {
        value 1;
        description
          "dhcp enable";
      }
    }
    description
      "dhcp disable or enable";
  }
  
  typedef dhcp-type {
    type enumeration {
      enum none {
        value 1;
        description "No dhcp function";
      }
      enum relay {
        value 2;
        description "Dhcp relay function";
      }
	  enum server {
        value 3;
        description "Dhcp server function";
      }
    }
    description "Dhcp function type";
  }

  typedef option82-policy-enum {
    type enumeration {
      enum drop {
        value 1;
        description "If contain option82, than drop";
      }
      enum keep {
        value 2;
        description "If contain option82, do nothing";
      }
	  enum remove {
        value 3;
        description "If contain option82, than remove";
      }
	  enum replace {
        value 4;
        description "If contain option82, than replace";
      }
    }
    description "Dhcp option82 policy";
  }

  typedef duid-type {
    type enumeration {
      enum ll {
        value 1;
        description "Dhcpv6 server identification, link layer address";
      }
      enum llt {
        value 2;
        description "Dhcpv6 server identification, link layer address and time";
      }
	  enum none {
        value 3;
        description "Dhcpv6 server identification, hex string";
      }
    }
    description "Dhcpv6 server unique identification type";
  }
  
  
  // grouping statements

  grouping option82-info {
    description
      "Dhcp option82 information";
    
    leaf option82-policy{
      type dhcp:option82-policy-enum;
      default keep;	
      description "Dhcp option82 policy";
    }
        
	  leaf option82-circuit-id {  
      type string{
        length "1..31";
      }
      description "Dhcp option82 circuit-id";
	  }
	  
	  leaf option82-remote-id {  
      type string{
        length "1..31";
      }
      description "Dhcp option82 remote-id";
	  }
  }
  
  grouping dhcp4-if-info {
    description
      "Dhcp4 interface configuration";
    
    leaf dhcp4-type{
      type dhcp:dhcp-type;
      default relay;	
      description "Dhcp4 function type";
    }
	
	container dhcp4-relay-if {
	  leaf source-ip {  
      type inet:ipv4-address-no-zone;
      description "Dhcp4 source-ip";
	  }
	  
	  leaf allow-mac-enable{
		type dhcp:dhcp-enable;
		default disable;
		description "allow mac enable";
      }
	  
	  leaf allow-mac-num {  
      type uint32{
		range "0..99999";
	  }
	  default 0;
      description "Dhcp4 allow-mac-num";
	  }
	  
	  leaf profile4-name {  
      type string{
        length "1..31";
		pattern "[^\s]+";
      }
      description "Dhcp4 profile4-name";
	  }
	}
	  
	container dhcp4-snooping-if {
		leaf snooping-trust{
		type dhcp:snooping-trust;
		default disable;	
		description "dhcp snooping function, Dhcp snooping-trust switch";
		}
	}
	  
  }
  
  grouping dhcp6-if-info {
    description
      "Dhcp6 interface configuration";
    
    leaf dhcp6-type{
      type dhcp:dhcp-type;
      default relay;	
      description "Dhcp6 function type";
    }
    
	container dhcp6-relay-if {
      leaf profile6-name {  
      type string{
        length "1..31";
		pattern "[^\s]+";
      }
      description "Dhcp6 profile6-name";
	  }
	}
	    
	container dhcp6-server-if {
      leaf pool6-name {  
      type string{
        length "1..32";
      }
      description "Dhcp6 server pool6 name";
	  }
	}
  }
  
  grouping dhcp4-client-option {
    description
      "Dhcp4 client option information";
    
    leaf client-id{
      type string{
        length "1..31";
      }	
      description "Dhcp4 client client-id, option61";
    }
        
    leaf hostname{
      type string{
        length "1..31";
      }	
      description "Dhcp4 client hostname, option12";
    }
    
    leaf vendor-id{
      type string{
        length "1..31";
      }	
      description "Dhcp4 client vendor-id, option60";
    }
    
    leaf vi-vendor-id{
      type string{
        length "1..63";
      }	
      description "Dhcp4 client vi-vendor-id, option125";
    }
  }
  
  container dhcp {
  
	  container dhcp4 {
		 container dhcp4-global-cfg {
			description
			  "Dhcp4 global configuration";
			
		  
			container dhcp4-global-relay {
				description
					"Dhcp4 global configuration";
					
				leaf relay-hops-max {  
				  type uint8{
					range "0..255";
				  }
				  default 255;
				  description "Dhcp4 relay max hops";
				}
			}
		 }
			
		 container profile4-relays {
			list profile4-relay{
			  key "name";
			  description "Dhcp4 relay profile name";
			  
			  leaf name {  
				type string{
				  length "1..31";
				  pattern "[^\s]+";
				}
				description "Dhcpv4 relay profile name";
			  }
				
			  uses option82-info;
				
			  list profile4r-relay-addr {
				key "relay-addr";
				description "Dhcp4 relay address";
				
				leaf relay-addr {  
				  type inet:ipv4-address-no-zone;
				  description "Dhcp4 relay address";
				}
			  }
			}
		 }
			
		 container dhcp4-interfaces {
			list dhcp4-interface{
			  key "if-name";
			  description "Dhcp4 interface name";
			  
			  leaf if-name {  
				type dhcp:if-ref;
				description "Dhcpv4 interface name";
			  }
				
			  uses dhcp4-if-info;
			  
        container dhcp4c-interface {       
          leaf dhcpv4c_enable{
            type dhcp:dhcp-enable;
            default enable;
            description "Dhcpv4 client interface enable";
          } 
        }
 
        container dhcp4c-option {       
          uses dhcp4-client-option;
        }
			}
		 }
	  }
	  
	  container dhcp6 {
		 container dhcp6-global-cfg {
			description
			  "Dhcp6 global configuration";
			  
			container dhcp6-global-server {
				description
					"Dhcp6 global configuration";
			  
				leaf duid-type{
				  type dhcp:duid-type;
				  default llt;	
				  description "Dhcpv6 server unique identification type";
				}
				
				leaf server-duid {  
				  type string{
					length "1..128";
				  }
				  description "Dhcp6 server duid";
				}
			}
		 }
			
		 container profile6-relays {
			list profile6-relay{
			  key "name";
			  description "Dhcp6 profile name";
			  
			  leaf name {  
				type string{
				  length "1..31";
				  pattern "[^\s]+";
				}
				description "Dhcpv6 profile name";
			  }

			  list profile6r-relay-addr {
				key "relay-addr";
				description "Dhcp6 relay address";
				
				leaf relay-addr {  
				  type inet:ipv6-address-no-zone;
				  description "Dhcp6 relay address";
				}
			  }
			}
		 }
			
		 container dhcp6-interfaces {
			list dhcp6-interface{
			  key "if-name";
			  description "Dhcp6 interface name";
		 
			  leaf if-name {  
				type dhcp:if-ref;
				description "Dhcpv6 interface name";
			  }
			
			  uses dhcp6-if-info;
			}
		 }  
	  }
  }
  
 
  
  // data definition statements

  // augment statements

}
