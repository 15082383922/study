module chinaunicom-evpn{

  /*** NAMESPACE / PREFIX DEFINITION ***/

  namespace "http://chinaunicom.com/yang/vpnservice/chinaunicom-evpn";

  prefix "evpn";

  /*** LINKAGE (IMPORTS / INCLUDES) ***/
  import chinaunicom-datatype-common  {	revision-date 2020-08-14; prefix "co-type"; }
  
  import chinaunicom-interface-common  {	revision-date 2020-12-31; prefix "if"; }
  
  import chinaunicom-tunnelpolicy	{	revision-date 2018-01-05; prefix "tnl-plcy"; }
  
  import ietf-inet-types {	revision-date 2013-07-15; prefix "inet"; }  

  /*** META INFORMATION ***/

  organization "Fiberhome Systems, Inc.";

  contact
    "Fiberhome Systems, Inc.
     
		Postcode: 430073 
		Address: No.6,Gaoxin 4 Rd,Donghu Hi-Tech Development Zone, Wuhan, Hubei
		Tel: +XXXXXXXXXXXX

		E-mail: yang- author@fiberhome.com";


  description 
    "This module contains a collection of YANG definitions
     for Fiberhome chinaunicom-R8000 l2vpn package configuration.

     This module contains definitions
     for the following management objects:
       l2vpn: Layer 2 VPN configuration

     Copyright (c) 2013-2016 by Fiberhome Systems, Inc.
     All rights reserved.";
	 
	revision 2020-11-27 {
    description 
      "modified by UT liufeng. EVPN is for EVPN-VPLS,EVPN-VPWS is for EVPN-VPWS,evpl binding EVPN-VPWS";
 }
     revision 2020-07-07{
     description 
     "Add typedef locator-name;
         Delete typedef is-switch;
         In typedef mode-type, add enum srv6;
         In container evpls, modify leaf evpn-name to evpl name;
         In container evpls, add leaf mode-type;
         In container evpls, add leaf binding-evpn-name;
         In container evpls, in container neighbor-pws, add leaf locator-name and leaf auto-sid-disable;
         In container evpls, move leaf pm-statistic-enable from list evpl to container neighbor-pws;
         In container evpls, delete leaf is-switch;
         In container evpls, delete leaf s-remote-service-id;
         In container evpls, delete leaf s-local-service-id;
         In augment, in container evpn-binding, add leaf locator-name and leaf auto-sid-disable. ";
 }

	revision 2020-03-09 {
    description 
      "Add pm-statistic-enable to evpls and evpn-binding containers;
	   Delete evpn-name of neighbor-pws, Modify evpl-name to evpn-name;
	   Add mode-type,eth-tag and ac-split-horizon to evpn-binding containers.";
  }
  
    revision 2019-12-25 {
    description 
      "Add member pw-ve-name in if-ref.";
  }
  
    revision 2019-10-24 {
    description 
      "Modify member vni is import form vxlan.";
  }

    revision "2017-11-23" {
    description
      "chinaunicom R8000 6.0 revision.";
  }
  
  /* typedefs */
  typedef evpn-name{
    type string{
	  length "1..31";
	}
	description "evpn name";
  }

  /* typedefs */
  typedef evpn-vpws-name{
    type string{
	  length "1..31";
	}
	description "evpn name";
  }
  
  /* typedefs */
  typedef evpl-name{
    type string{
	  length "1..31";
	}
	description "evpl-name";
  }
  
  typedef if-ref {
	type union {
		type if:ethphy-name;
		type if:ethlag-name;
		type if:ethsub-name;
		type if:pw-ve-name;
	}
	description "UNI interfaces name ref";
  }
  
  typedef tnlplcy-ref {
	type tnl-plcy:policy-name;
	
	description "Tunnel policy name ref";
  }
    
  typedef community-extend{
	    type string{
		     pattern  '((((([1-9]|[1-9][0-9]|1[0-9][0-9]|2[0-4][0-9]|25[0-5])\.)'+
					'(([0-9]|[1-9][0-9]|1[0-9][0-9]|2[0-4][0-9]|25[0-5])\.){2}'+
					'([0-9]|[1-9][0-9]|1[0-9][0-9]|2[0-4][0-9]|25[0-5]):)'+
					'(6553[0-5]|655[0-2][0-9]|65[0-4][0-9]{2}|6[0-4][0-9]{3}|[1-5][0-9]{4}|[1-9][0-9]{0,3}|0))|'+
					'((6553[0-5]|655[0-2][0-9]|65[0-4][0-9]{2}|6[0-4][0-9]{3}|[1-5][0-9]{4}|[1-9][0-9]{0,3}):'+
					'(429496729[0-5]|42949672[0-8][0-9]|4294967[01][0-9]{2}|429496[0-6][0-9]{3}|42949[0-5][0-9]{4}|'+
					'4294[0-8][0-9]{5}|429[0-3][0-9]{6}|42[0-8][0-9]{7}|4[01][0-9]{8}|[1-3][0-9]{9}|[1-9][0-9]{0,8}|0)))';
		}
		description "community-extend type";
   }
   
   typedef rt-type{
    type enumeration {
	  enum import {
		value 1;
		description "import for route target type";
	  }
	  enum export {
		value 2;
		description "export for route target type";
	  }
	  enum both {
		value 3;
		description "both for route target type";
	  }
	}
    description "l3vpn route target type";
  }
  
  typedef esi-value{
	    type string{
		     pattern '((([0-9]|[a-f])([0-9]|[a-f]))\.){8}(([0-9]|[a-f])([0-9]|[a-f]))';
			 length "0..26";
		}
		description "esi value";
   }
	
  typedef active-type {
    type enumeration {
      enum all-active{
        value 0;
        description "all-active";
      }
      enum single-active{
        value 1;
        description "single-active";
      }
    }
    description "active type";
  }
  
  typedef esi-type {
    type enumeration {
      enum esi-type0{
        value 0;
        description "esi type zero";
      }
    }
    description "evpn esi types";
  }

 
  /* EVPN YANG Model */
  container evpn {
		leaf evpn-source-ipaddress{
		description
			  "Specifies source ipaddress for evpn.";
			type inet:ipv4-address-no-zone;
			}
			
		container evpn-esi-interfaces {
			description "evpn esi interfaces";
		   
			list evpn-esi-interface{
				key "ifname";
				description "physical interface for esi";
		
				leaf ifname{
					type if-ref;
					description "interface name";
				}
		
				leaf ethernet-segment-enable{
					type co-type:is-enable;
					description "ethernet segment enable";
				}
		   
				leaf ethernet-segment-type{
					type esi-type;
					description "ethernet segment type";
				}
		
				leaf ethernet-segment-identifier{
					type esi-value;
					description "ethernet segment identifier value";
				}
		
				leaf active-type{
					type active-type;
					description "active type";
				}
			}
		}			
			
		container evpn{	
			description "evpn vpls configuration";
			list evpn-list{
				key "evpn-name";
				description "evpn instance name";
			
				leaf evpn-name{
					type evpn-name;
					description "evpn name";
				}
			
				leaf tunnel-policy{
					type tnlplcy-ref;
					description "tunnel policy name";
				}
			
				leaf route-distinguisher{
					type community-extend;
					description "route distinguisher";
				}
			
				list route-target-list{
					key "route-target route-target-type";
			
					leaf route-target{
						type community-extend;
						description "route target";
					}
			  
					leaf route-target-type{
						type rt-type;
						description "route target type";
					}
				}
				
				list accessif-list{
					key "ac-name";
					description "attachment circuit interface";
				
					leaf ac-name{
						type if-ref;
						description "interface name";
					}

					leaf ac-split-horizon{
					   type co-type:is-enable; 
					   default "disable";
					   description "enable split horizon on AC";
					}
				}
				
			}

		}

		container evpn-vpws{	
			description "evpn vpws configuration";
			list evpn-vpws-list{
				key "evpn-vpws-name";
				description "evpn-vpws instance name";
			
				leaf evpn-vpws-name{
					type evpn-vpws-name;
					description "evpn-vpws-name";
				}
			
				leaf tunnel-policy{
					type tnlplcy-ref;
					description "tunnel policy name";
				}
			
				leaf route-distinguisher{
					type community-extend;
					description "route distinguisher";
				}
			
				list route-target-list{
					key "route-target route-target-type";
			
					leaf route-target{
						type community-extend;
						description "route target";
					}
			  
					leaf route-target-type{
						type rt-type;
						description "route target type";
					}
				}
						
			}

		}
	 
		container evpl {
			description "evpn evpl";
		   
			list evpl{
				key "evpl-name";
				description "evpl instance name";
		
				leaf evpl-name{
					type evpl-name;
					description "evpl name";
				}
						
				leaf ac-name{
					type if-ref;
					description "interface name";
				}							

				leaf binding-evpn-name{
					type evpn-name;
					description "binding evpn name";
				}
	
				leaf remote-service-id{
					type uint32{
						range "1..16777215";
					}
					description "remote service id";
				}
		
				leaf local-service-id{
					type uint32{
						range "1..16777215";
					}
					description "local service id";
				}

				}
			}     
		}
	}
