module chinaunicom-device-oper {

  namespace "http://chinaunicom.com/yang/devicemanager/chinaunicom-device-oper";

  prefix "device-oper";
  import chinaunicom-datatype-common {	revision-date 2020-08-14; prefix "co-type"; }
  import ietf-yang-types {	revision-date 2013-07-15;prefix "yang";}
  import chinaunicom-extension {	revision-date 2020-03-30; prefix "ext"; }
  
  organization "Fiberhome Systems, Inc.";

  contact
    "Fiberhome Systems, Inc.
    Postcode: 430073
    Address: No.6,Gaoxin 4 Rd,Donghu Hi-Tech Development Zone, Wuhan, Hubei
    Tel: +XXXXXXXXXXXX
    
    E-mail: yang- author@fiberhome.com";

  description
    "This module contains a collection of YANG definitions
    for Fiberhome device info.
    
    This module contains definitions
    for the following management objects:
         ***
    E-mail: yang- author@fiberhome.com
    All rights reserved.";
    
  revision "2020-12-31" {
    description
      "revise names of notification and their leaves";
	}
    
  revision "2020-12-13" {
    description
      "revise length of leaf reg-info, deleate caotainer
      neighbor-device-infos and rpc update-mode,add description 
      for leaf material and container bmustatus-infos.
      deleate leaf loc of container cardtemp-infos";
	}
	
    revision "2020-09-07" {
    description
    	"Add notification for telemetry.";
	}


  revision "2018-11-15" {
    description
      "chinaunicom 1.0 revision.";
	}
	
	typedef switchover-state-type{
	  type enumeration {
      enum READY {
        value 1;
        description "READY";
      }
      enum NO-SLAVE {
        value 2;
        description "NO-SLAVE";
      }
	   enum BATCH-BACKUP {
        value 3;
        description "BATCH-BACKUP";
      }
	   enum BACKUP-FAULT {
        value 4;
        description "BACKUP-FAULT";
      }
	   enum ERROR {
        value 5;
        description "ERROR";
      }
	  enum NO-READY{
        value 6;
        description "NO-READY";
      }
    }
    description "switchover-state-type";
  }
  
  typedef board-state-type{
	type enumeration {
	enum INACTIVE {
		value 0;
		description "INACTIVE";
		}
	enum ACTIVE {
		value 1;
		description "ACTIVE";
		}
	}
  }
	
	typedef active-type {
    type enumeration {
      enum active {
        value 0;
        description "active";
      }
      enum unactive {
        value 1;
        description "unactive";
      }
    }
	description "active-type";
  }
	
	
	typedef register-type {
    type enumeration {
      enum register {
        value 0;
        description "register";
      }
      enum unregister {
        value 1;
        description "unregister";
      }
    }
	description "register-type";
  }
	

  
  typedef chassis-role {
    description "chassis role";
      type enumeration {
        enum main-chassis {
          value 0;
          description "main chassis";
        }
        enum ext-chassis {
          value 1;
          description "ext chassis";
        }      
      }
    }

 
 typedef power-type {
    description "fanctrl power type";
      type enumeration {
        enum down {
          value 0;
          description "down";
        }
        enum up {
          value 1;
          description "up";
        }      
      }
    }
    
    
  typedef board-type {
    type enumeration {
      enum MPU {
        value 1;
        description "MPU";
      }
      enum LPU {
        value 2;
        description "LPU";
      }
      enum PIU {
        value 3;
        description "PIU";
      }
      enum MSC {
        value 4;
        description "MSC";
      }
      enum SFU {
        value 5;
        description "SFU";
      }
      enum PWR {
        value 6;
        description "PWR";
      }
      enum FAN {
        value 7;
        description "FAN";
      }
    }
    description
      "enumeration board type";
  }
  
  typedef board-status {
    type enumeration {
      enum OK {
        value 1;
        description "OK";
      }
      enum DOWN {
        value 2;
        description "DOWN";
      }
      enum INTERRUPT {
        value 3;
        description "INTERRUPT";
      }
      enum WRONG {
        value 4;
        description "WRONG";
      }
    }
    description
      "enumeration board status";
  }
	
    
  grouping  chassis-info {
    description "chassis info";
    
  leaf role{
type chassis-role;  
description "chassis role";
  }
    
  leaf chassis-num{
type co-type:shelf-num-string;
description "chassis unmber";
  }

    leaf chassis-name {
        type string {
            length "1..32";
        }
        description "chassis name";
    }

    leaf snid {
        type string {
            length "1..32";
        }
        description "chassis sn unmber";
    }

    leaf main-board-name {
        type string {
            length "1..32";
        }
        description "main board name";
    }

    leaf main-board-slot-num {
        type co-type:slot-num-string;
        description "main board slot unmber";
    }
  }

  grouping board-trap-common
  {
      leaf SlotNo {
        type uint16;
      }
	  
      leaf BoardType {
        type board-type;
      }

      leaf BoardStatus {
        type board-status;
      }

      leaf BoardName {
        type string {
          length 0..64;
        }
      }
  }

  
  container device-oper {

	config false;
		description "device information";
		
		container device-info-status {
			description "device status information.";
			
			leaf rack {
				type uint8 {
					range "0..255";
				}
				description
				"sn id which uniquely identifies a device";
			}
			
			leaf uuid {
				type string {
					length "1..32";
				}
				description
				"device id which uniquely identifies a device";
			}
		
			leaf snid {
				type string {
					length "1..32";
				}
				description
				"sn id which uniquely identifies a device";
			}
		
			leaf device-type { 
				type string {
					length "1..64";
				}
				description
				"device type, eg:switch/vbras/cer....if cann't obtion device type,
				this item can be ignore ";
			}

			leaf hardware-version {
				type string {
					length "1..32";
				}
				description
				"device hardware version.";
			}
		
			leaf software-version { 
				type string {
					length "1..32";
				}
				description
				"device software version.";
			}
		
			leaf manufacturer {
				type string {
					length "1..32";
				}
				description
				"device manufacturer info.eg:fiberhome";
			}
			leaf cpu-info {
				type string {
					length "1..256";
				}
				description
				"cpu info of device. format is :core:4, frequency:2G, 64 bit processor";
			}
			leaf memory {
				type string {
					length "1..256";
				}
				description
				"device's total memory.eg:4096M or 4G";
			}
			
			leaf esnid {
				type string {
					length "1..64";
				}
				description
				"esn id which uniquely identifies a device";
			}
		}	
			
		container board-inchinaunicom {
			description "board state infomation.";
		
		list board-info{
			key "slot-num cpu-num";
						
			leaf uptime {
				type string {
				length "0..31";
				}
			}
				
			leaf name {
				type string {
				length "0..31";
				}
			}				
		
			leaf role {
				type string {
				length "0..15";
				}
			}
						
			leaf reg-info {
				type string {
				length "0..64";
				}
			}
		
			leaf init-info {
				type string {
				length "0..7";
				}
			}
		
			leaf online {
				type string {
				length "0..7";
				}
			}
				
			leaf software-version {
				type string {
				length "1..64";
				}
			}
				
			leaf pcb-version {
				type string {
				length "1..64";
				}
			}
			
			leaf board-version {
				type string {
				length "1..64";
				}
			}
			
			leaf complie-time {
				type string {
				length "1..64";
				}
			}
			
			leaf board-state {
				type string {
				length "1..32";
				}
			}
			
			leaf board-sn {
				type string {
				length "1..32";
				}
			}
				
			leaf board-type {
				type string {
				length "1..32";
				}
			}
				
			leaf slot-num {
				type co-type:slot-num-string;					
			}
															
			leaf cpu-num {
				type uint8 {
				range "0..255";
				}
			}
		}
		}
		container board-state-inchinaunicom {
		description
			"board state information";	
		list board-state-info {
		key "slot-id";
			leaf slot-id {
				type co-type:slot-num-string;
				description
				"slot id which uniquely identifies a board.";
			}
			
			leaf board-version {
				type string {
					length "1..64";
				}
				description
				"board version";
			}
			
			leaf pcb-version {  
				type string {
					length "1..64";
				}
				description
				"pcb version";
			}

			leaf software-version {
				type string {
					length "1..64";
				}
				description
				"board software version.eg:RP0100";
			}
			
			leaf shelf-type {
				type string {
					length "1..64";
				}
				description
				"type of the shelf .eg:CITRANS8010";
			}
			leaf main-src-slot {
				type co-type:slot-num-string;
				description
				"the slot of the main src";
			}
			leaf power-on-time {
				type string {
					length "1..64";
				}
				description
				"time during the board power on";
			}
			
			leaf register {
				type register-type;
				description
				"register or not register";
			}
			leaf active  {
				type active-type;
				description
				"active or not unactive";
			}
		}
		}
		
		container board-filesystem-usages {
		description
			"board filesystem information.";
		list board-filesystem-usage {
			key "slot-id filesystem";
			description
			"filesystem information.";
			
			leaf slot-id {
			    type co-type:slot-num-string;
				description
				"slot id which uniquely identifies a slot";
			}
		
			leaf filesystem {
				type string {
					length "1..32";
				}
			}
		
			leaf size {  
				type string {
					length "1..32";
				}
			}

			leaf used {
				type string {
					length "1..32";
				}
				description
				"use value";
			}
		
			leaf avail {   
				type string {
					length "1..32";
				}
			}
		
			leaf use {
				type string {
					length "1..32";
				}
				description
				"use percent";
			}
		

			leaf mounted-on {
				type string {
					length "1..32";
				}
			}
		}
	}
		
		container system-usage-slots {
		description
			"board system usage information.";	
		list system-usage-slot {
			key "slot-id";
			leaf slot-id {
			type co-type:slot-num-string;
				description
				"slot id which uniquely identifies a board";				
			}
			
			leaf cpu-usage {
				type string {
					length "1..32";
				}
			}
			
			leaf memory-usage { 
				type string {
					length "1..32";
				}
			}
		}
	  }
	  
	  container board-switchover-info {
		description
			"switch-over information";	
			leaf switchover-state{
				type switchover-state-type;
				description
					"switchover-stat";
			}
			
			leaf mainboard-slot {  
				type co-type:slot-num-string;
				description
					"mainboard-slot";
			}
			
			leaf slaveboard-slot {  
				type co-type:slot-num-string;
				description
					"slaveboard-slot";
			}

		}


      container fan-inchinaunicom {
			description "fans infomation.";
		
			list fan-info{
				key "slot-id";		
						
				leaf slot-id {
				type co-type:slot-num-string;
				description
				"slot id which uniquely identifies a board.";
			 }	
		
				leaf board_info {
					type string {
					length "0..20";
					}
				}
						
				leaf material {
				description "leaf material is optional.";
					type string {
					length "0..20";
					}
				}
		
				leaf sn {
					type string {
					length "0..20";
					}
				}
		
				leaf status {
					type string {
					length "0..20";
					}
				}
				
				leaf level {
					type uint8 {
					range "0..255";
					}
				}
				
				leaf speed {
					type uint16 {
					range "0..65535";
					}
				}
			
				leaf board-pcb {
					type string {
					length "1..64";
					}
				}
			
				leaf board-ver {
					type string {
					length "0..20";
					}
				}
				
			}
		}
		
		container power-inchinaunicom {
			description "powers infomation.";
		
			list power-info{
				key "slot-id";
						
				leaf slot-id {
				type co-type:slot-num-string;
				description
				"slot id which uniquely identifies a board.";
			 }	
		
				leaf board_info {
					type string {
					length "0..20";
					}
				}
						
				leaf material {
				description "leaf material is optional.";
					type string {
					length "0..20";
					}
				}
		
				leaf sn {
					type string {
					length "0..20";
					}
				}
			
				leaf board-pcb {
					type string {
					length "1..64";
					}
				}
			
				leaf board-ver {
					type string {
					length "0..20";
					}
				}
				
			}
		}
		
		 container cardtemp-inchinaunicom {
			description "cardtemp infomation.";
		
			list cardtemp-info{
				key "slot-id";
						
				leaf slot-id {
				type co-type:slot-num-string;
				description
				"slot id which uniquely identifies a board.";
			 }			
		
				leaf board_name {
					type string {
					length "0..20";
					}
				}
						
				leaf temp {
					type int32 {
					range "-256..256";
					}
				}
		
				leaf tref_val {
					type int32 {
					range "-256..256";
					}
				}
				
				leaf tmax_val {
					type int32 {
					range "-256..256";
					}
				}
				
				leaf tdiff {
					type int32 {
					range "-256..256";
					}
				}
				
			}
		}
		
		container uptime-inchinaunicom {
			description "uptime infomation.";	
		
				leaf uptime {
					type string {
					length "0..30";
					}
				}
		  }
		
		 container subframe-inchinaunicom {
			description "subframe infomation.";
		
			list subframe-info{
				key "chassis-no";
						
				leaf chassis-no {
				type co-type:shelf-num-string ;
				description
				"chassis no which uniquely identifies a board.";
			  }		
				
				leaf mainboard_mac {
				  type yang:mac-address;
          description "mainboard MAC address";
				}				
		
				leaf info {
					type string {
					length "0..20";
					}
				}
						
				leaf sn {
					type string {
					length "0..20";
					}
				}
		
				leaf board_ver {
					type string {
					length "0..20";
					}
				}
				
			}
		}
		
		 container bmustatus-inchinaunicom {
			description "bmustatus infomation. this container is optional";
		
			list bmustatus-info{
				key "slot-id";
						
				leaf slot-id {
				type co-type:slot-num-string;
				description
				"slot id which uniquely identifies a board.";
			 }		
		
				leaf bmu_volt {
					type int32 {
					range "-256..500";
					}
				}
						
				leaf bmu_power {
					type int32 {
					range "-256..500";
					}
				}
		
				leaf bmu_temp {
					type int32 {
					range "-256..500";
					}
				}
				
			}
		}
		
		container version-inchinaunicom {
			description "version state informaiton";
			
			list version-info {
				key "slot";	
				leaf name {
					type string {
					length "1..16";
					}
				}
					
				leaf slot {
					type co-type:slot-num-string;
				}
					
				leaf board-version {
					type string {
					length "1..64";
					}
				}
					
				leaf pcb-version {
					type string {
					length "1..64";
					}
				}
					
				leaf software-version {
					type string {
					length "1..64";
					}
				}
					
				leaf build-time {
					type string {
					length "1..64";
					}
				}
			}	
		}		
		
        container system-mac-inchinaunicom{
		description "system-mac inchinaunicom";
			
			leaf system-mac-start {
				type yang:mac-address;
			}
				
			leaf system-mac-end {
				type yang:mac-address;
			}
			
			leaf system-mac-num {
				type uint32 {
				range "0..4294967295";
				}
			}
			
			leaf logical-mac-start {
				type yang:mac-address;
			}
				
			leaf logical-mac-end {
				type yang:mac-address;
			}
			
			leaf logical-mac-num {
				type uint32 {
				range "0..4294967295";
				}
			}
			
			leaf all-physi-mac-start {
				type yang:mac-address;
			}
				
			leaf all-physi-mac-end {
				type yang:mac-address;
			}
			
			leaf all-physi-mac-num {
				type uint32 {
				range "0..4294967295";
				}
			}
			
		list physical-mac-info{
			key "physical-mac-index";
			
		    leaf physical-mac-index {
				type co-type:slot-num-string;
			}
			
			leaf physical-mac-start {
				type yang:mac-address;
			}
				
			leaf physical-mac-end {
				type yang:mac-address;
			}
			
			leaf physical-mac-num {
				type uint32 {
				range "0..4294967295";
				}
			}
	    }
	}
}
	
	

	
	/* SWITCH OVER   */
	rpc board-switch-over {
		output {	
			leaf switchover-result{
				type string {
					    length "1..256";
					}
				description
					"switchover-result";
			}
		}
	}
	
	/* SET BOARD ACTIVE */
	rpc set-board-state-cmd {
		input {
			leaf  slot-id {
				type co-type:slot-num-string;
				description 
					"board_slot_id";	
			}
			leaf  active-status{
				type board-state-type;
				description 
					"board_active_status";	
			}
		}	
	}
		
		/* POWER CMD RPC */
	rpc power-cmd {
		description "power up/down";
		input {	
				leaf power-ctrl {
					type power-type ;
					default up; 
				}
				
				leaf chassis-no {
				type co-type:shelf-num-string ;
				description
				"chassis no which uniquely identifies a board.";
			  }	
				
				leaf slot-no {
					type uint16 {
						range "0..65535";
					}
				}
				
			}
		}
		

	/* UPDATE MODE */
	rpc update-mode {
        input {
			leaf  slot-id {	
				type co-type:slot-num-string;
				description 
					"slot-id";
			}
		}
    }
	

  notification MemoryUsageExceed {
    ext:telemetry-available;
    description
     "The board MemoryUsageExceed will send this trap.";

    uses board-trap-common;
  }

  notification MemoryUsageNormal {
    ext:telemetry-available;
    description
     "The board MemoryUsageNormal will send this trap.";

    uses board-trap-common;
  }

  notification FlashUsageExceed {
    ext:telemetry-available;
    description
     "The board FlashUsageExceed will send this trap.";

    uses board-trap-common;
  }

  notification FlashUsageNormal {
    ext:telemetry-available;
    description
     "The board FlashUsageNormal will send this trap.";

    uses board-trap-common;
  }

  notification CPUUsageExceed {
    ext:telemetry-available;
    description
     "The board CPUUsageExceed will send this trap.";

    uses board-trap-common;
  }

  notification CPUUsageNormal {
    ext:telemetry-available;
    description
     "The board CPUUsageNormal will send this trap.";

    uses board-trap-common;
  }
  
  notification BoardNotExist {
    ext:telemetry-available;
    description
     "The board pull out action will send this trap.";

    uses board-trap-common;
  }

  notification BoardExist {
    ext:telemetry-available;
    description
     "The board push in action will send this trap.";

    uses board-trap-common;
  }
		
}
