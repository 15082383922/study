module chinaunicom-rfc2544-oper{

  /*** NAMESPACE / PREFIX DEFINITION ***/

  namespace "http://chinaunicom.com/yang/systemdiagnose/chinaunicom-rfc2544-oper";


  prefix "rfc2544-oper";

  /*** LINKAGE (IMPORTS / INCLUDES) ***/

  import chinaunicom-datatype-common {	revision-date 2020-08-14; prefix "co-type"; }

  import ietf-yang-types {	revision-date 2013-07-15; prefix "yang"; }

  import chinaunicom-interface-common {	revision-date 2020-12-31; prefix "if"; } 

  //import ietf-inet-types {	revision-date 2013-07-15; prefix "inet"; }
  
  //import chinaunicom-l3vpn  {	revision-date 2019-10-24; prefix "l3vpn"; }
  

  /*** META INFORMATION ***/

  organization "UTStarcom Telecom Co., Ltd.";

  contact
    "UTStarcom Telecom Co., Ltd.
     
     Postcode: 310053 
     Address: 368 Liuhe Road, Binjiang District,Hangzhou, Zhejiang

     E-mail: sheng.yu@utstar.com";
     
  description 
    "This module contains a collection of YANG definitions
     for UTStarcom IPRAN rfc2544 operational configuration.
     Copyright (c) 2013-2020 by UTStarcom Telecom Co., Ltd.
     All rights reserved.";

  revision "2020-12-10" {
    description
      "1. first revision.
       2. remove unused import modules to keep the compiler silence.";
  }
  
    typedef if-ref {
		type union {
			type if:ethphy-name;
			type if:ethlag-name;
			type if:veth-name;
			type if:ethsub-name;
		}
	}
	
	typedef test-result {
    type enumeration {
		  enum fail {
				value 1;
				description "fail";
		  }
		  enum success {
				value 2;
				description "success";
		  }
		  enum running {
				value 3;
				description "running";
		  }
		  enum waiting {
				value 4;
				description "waiting";
		  }
		  
		}
	}
	
	typedef test-time {
		type string {
			length "0..20";
		}
		description "test-time";
	}
	
	typedef test-state {
    type enumeration {
		  enum not-started {
				value 1;
				description "not-started";
		  }
		  enum testing {
				value 2;
				description "testing";
		  }
		  enum completed {
				value 3;
				description "completed";
		  }
		}
	}
	
	typedef start-type {
    type enumeration {
		  enum now {
				value 1;
				description "now";
		  }
		  enum delay {
				value 2;
				description "delay";
		  }
		  enum start-at {
				value 3;
				description "start-at";
		  }
		}
	}
	
	container rfc2544-oper{
	  config false;
	  description "rfc2544-oper top container";
		container rfc2544-sender-states-cfg{ 
			description "rfc2544 sender states cfg container"; 
			list rfc2544-sender-state-list{
				key sender-id;
				leaf sender-id {
					type uint32 {
						range "1..32";
					}
					description "sender-id";
				}
				leaf sender-interface {
					type string;
					description "sender-interface";
				}
				leaf mac {
					type yang:mac-address;
					description "mac";
				}
				leaf start-time {
					type rfc2544-oper:test-time;
					description "start-time";
				}
				leaf stop-time {
					type rfc2544-oper:test-time;
					description "stop-time";
				}
				leaf throughput-test-result {
					type rfc2544-oper:test-result;
					description "throughput-test-result";
				}
				leaf loss-test-result {
					type rfc2544-oper:test-result;
					description "loss-test-result";
				}
				leaf delay-test-result {
					type rfc2544-oper:test-result;
					description "delay-test-result";
				}
				leaf test-state {
					type rfc2544-oper:test-state;
					description "test-state";
				}						
			}
		}
		
		container rfc2544-sender-throughput-states-cfg{ 
			description "rfc2544 sender throughput states cfg container"; 
			list rfc2544-sender-throughput-state{
				key sender-id;
				leaf sender-id {
					type uint32 {
						range "1..32";
					}
					description "sender-id";
				}
				list rfc2544-sender-throughput-state-list{
					key packet-length;
					leaf packet-length {
						type uint16 {
							range "64..1518";
						}
						description "packet-length";
					}
					leaf throughput {
						type uint32 {
							range "0..100000000";
						}
						description "The unit is Kbit/s.";
					}
					leaf test-result {
						type rfc2544-oper:test-result;
						description "test-result";
					}						
				}
			}
		}
		
		container rfc2544-sender-loss-states-cfg{ 
			description "rfc2544 sender loss states cfg container";
			list rfc2544-sender-loss-state{
				key sender-id;
				leaf sender-id {
					type uint32 {
						range "1..32";
					}
					description "sender-id";
				}
				list rfc2544-sender-loss-state-list{
					key packet-length;
					leaf packet-length {
						type uint16 {
							range "64..1518";
						}
						description "packet-length";
					}
					leaf send-packet {
						type uint64;
						description "send-packet";
					}
					leaf loss-packet {
						type uint64;
						description "loss-packet";
					}
					leaf loss-rate {
						type co-type:float6;
						description "loss-rate";
					}
					leaf test-result {
						type rfc2544-oper:test-result;
						description "test-result";
					}						
				}
			}
		}
		
		container rfc2544-sender-delay-states-cfg{ 
			description "rfc2544 sender delay states cfg container";
			list rfc2544-sender-delay-state{
				key sender-id;
				leaf sender-id {
					type uint32 {
						range "1..32";
					}
					description "sender-id";
				}
				list rfc2544-sender-delay-state-list{
					key packet-length;
					leaf packet-length {
						type uint16 {
							range "64..1518";
						}
						description "packet-length";
					}
					leaf average-delay {
						type uint64;
						description "average-delay";
					}
					leaf delay-variation {
						type uint64;
						description "delay-variation";
					}
					leaf test-result {
						type rfc2544-oper:test-result;
						description "test-result";
					}						
				}
			}
		}
	}
	
	rpc set-rfc2544-sender-switch {
		input {
			leaf sender-id {
				type uint32 {
					range "1..4294967295";
				}
				description "sender-id";
			}
			leaf start-type {
				type rfc2544-oper:start-type;
				default now;
				description "start-type";
			}
			leaf delay-seconds {
				type uint32 {
					range "1..86399";
				}
				description "delay-seconds";
			}
			leaf start-time {
				type rfc2544-oper:test-time;
				description "start-time";
			}
			leaf test-onoff {
				type co-type:is-enable;
				description "test-onoff";
			}
		}
	}
}
